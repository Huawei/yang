/*
Copyright (C) 2020 Huawei Technologies Co., Ltd. All rights reserved.
*/
module huawei-if-ip-deviations-NE-X1X2 {
  namespace "urn:huawei:yang:huawei-if-ip-deviations-NE-X1X2";
  prefix if-ip-devs-NE-X1X2;

  import huawei-if-ip {
    prefix if-ip;
  }
  import huawei-network-instance {
    prefix ni;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2020-09-28 {
    description
      "Init revision.";
    reference "Huawei private.";
  }

  deviation "/ni:network-instance/ni:instances/ni:instance/if-ip:ipv4-ifs/if-ip:ipv4-if/if-ip:address/if-ip:config-address/if-ip:addresses/if-ip:address/if-ip:type" {
    deviate add {
      must "../if-ip:type='sub' and /ifm:ifm/ifm:global/ifm:ipv4-ignore-primary-sub='false' or ../if-ip:type='main'";
    }
  }
}
