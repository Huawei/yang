/*
Copyright (C) 2019 Huawei Technologies Co., Ltd. All rights reserved.
*/
module huawei-bras-vas-deviations-NE-X1X2 {
  namespace "urn:huawei:yang:huawei-bras-vas-deviations-NE-X1X2";
  prefix bras-vas-devs-NE-X1X2;

  import huawei-bras-vas {
    prefix bras-vas;
  }

  import huawei-devm {
    prefix devm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-vas module.";

  revision 2019-11-06 {
    description
      "Initial revision.";
    reference
      "Huawei private.";
  }

  deviation "/devm:devm/devm:mpu-boards/devm:mpu-board/bras-basic-access:bras/bras-vas:vas" {
    deviate not-supported;
  }

}
