/*
Copyright (C) 2020 Huawei Technologies Co., Ltd. All rights reserved.
*/
module huawei-lacp-deviations-CH-NE-X8X16 {
  yang-version 1;
  namespace "urn:huawei:yang:huawei-lacp-deviations-CH-NE-X8X16";
  prefix lacp-devs-CH-NE-X8X16;

  import huawei-lacp {
    prefix lacp;
  }
  import huawei-ifm-trunk {
    prefix ifm-trunk;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "Link Aggregation Control Protocol (LACP) management, which includes static LACP configuration, dynamic LACP learning.";

  revision 2020-05-18 {
    description
      "Initial revision.";
    reference "Huawei private.";
  }

  deviation "/lacp:lacp/lacp:global/lacp:m-lag" {
    deviate not-supported;
  }
  deviation "/ifm:ifm/ifm:interfaces/ifm:interface/ifm-trunk:trunk/lacp:lacp/lacp:m-lag" {
    deviate not-supported;
  }
}
