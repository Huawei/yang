/*
Copyright (C) 2019 Huawei Technologies Co., Ltd. All rights reserved.
*/
module huawei-mplsoam-deviations-CH-NE-X8X16 {
  yang-version 1;
  namespace "urn:huawei:yang:huawei-mplsoam-deviations-CH-NE-X8X16";
  prefix mplsoam-devs-CH-NE-X8X16;

  import huawei-mplsoam {
    prefix mplsoam;
  }

  organization
    "Huawei Technologies Co., Ltd.";
  contact
    "Huawei Industrial Base
     Bantian, Longgang
     Shenzhen 518129
     People's Republic of China
     Website: http://www.huawei.com
     Email: support@huawei.com";
  description
    "Multiprotocol Label Switching (MPLS) operations, administration and maintenance (OAM), provides the following functions: fault management, performance monitoring, and protection switching.";

  revision 2019-10-18 {
    description
      "Initial revision.";
    reference "Huawei private.";
  }

  deviation "/mplsoam:mplsoam/mplsoam:global/mplsoam:oam-num" {
    deviate not-supported;
  }
  deviation "/mplsoam:mplsoam/mplsoam:tunnels" {
    deviate not-supported;
  }
  deviation "/mplsoam:mplsoam/mplsoam:vll-pws" {
    deviate not-supported;
  }
  deviation "/mplsoam:mplsoam/mplsoam:vsi-pws" {
    deviate not-supported;
  }
  deviation "/mplsoam:enable-co-route-tunnel" {
    deviate not-supported;
  }
  deviation "/mplsoam:disable-co-route-tunnel" {
    deviate not-supported;
  }
  deviation "/mplsoam:enable-egress-id-tunnel-lsp" {
    deviate not-supported;
  }
  deviation "/mplsoam:disable-egress-id-tunnel-lsp" {
    deviate not-supported;
  }
  deviation "/mplsoam:enable-egress-name-tunnel-lsp" {
    deviate not-supported;
  }
  deviation "/mplsoam:disable-egress-name-tunnel-lsp" {
    deviate not-supported;
  }
  deviation "/mplsoam:enable-ingress-tunnel-lsp" {
    deviate not-supported;
  }
  deviation "/mplsoam:disable-ingress-tunnel-lsp" {
    deviate not-supported;
  }
  deviation "/mplsoam:enable-co-route-tunnel-lsp" {
    deviate not-supported;
  }
  deviation "/mplsoam:disable-co-route-tunnel-lsp" {
    deviate not-supported;
  }
}
