/*
Copyright (C) 2019 Huawei Technologies Co., Ltd. All rights reserved.
*/
module huawei-bras-cu-controller-deviations-CH-NE-X8X16 {
  namespace "urn:huawei:yang:huawei-bras-cu-controller-deviations-CH-NE-X8X16";
  prefix bras-cu-controller-devs-CH-NE-X8X16;

  import huawei-bras-cu-controller {
    prefix bras-cu-controller;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-cu-controller module.";

  revision 2019-11-06 {
    description
      "Initial revision.";
    reference
      "Huawei private.";
  }

  deviation "/bras-cu-controller:bras-cu-controller" {
    deviate not-supported;
  }
  deviation "/bras-cu-controller:reset-south-conflict-by-up" {
    deviate not-supported;
  }
  deviation "/bras-cu-controller:reset-south-conflict-all-up" {
    deviate not-supported;
  }

}
