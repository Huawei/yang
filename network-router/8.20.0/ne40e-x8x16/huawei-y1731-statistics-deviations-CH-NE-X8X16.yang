/*
Copyright (C) 2019 Huawei Technologies Co., Ltd. All rights reserved.
*/
module huawei-y1731-statistics-deviations-CH-NE-X8X16 {
  namespace "urn:huawei:yang:huawei-y1731-statistics-deviations-CH-NE-X8X16";
  prefix y1731-statistics-devs-CH-NE-X8X16;

  import huawei-y1731-statistics {
    prefix y1731-statistics;
  }

  import huawei-devm {
    prefix devm;
  }

  import huawei-y1731 {
    prefix y1731;
  }

  organization
    "Huawei Technologies Co., Ltd.";

  contact
    "Huawei Industrial Base
     Bantian, Longgang
     Shenzhen 518129
     People's Republic of China
     Website: http://www.huawei.com
     Email: support@huawei.com";

  description
    "This module defines deviation statements for huawei-y1731-statistics module.";

  revision 2019-11-06 {
    description
      "Initial revision.";
    reference
      "Huawei private.";
  }

  deviation "/y1731:y1731/y1731-statistics:inner-priority" {
    deviate not-supported;
  }
  deviation "/y1731:y1731/y1731-statistics:cfm-level-check" {
    deviate not-supported;
  }
  deviation "/devm:devm/devm:mpu-boards/devm:mpu-board/y1731-statistics:cfm-mac-level-enable-mpu" {
    deviate not-supported;
  }

}
