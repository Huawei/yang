/*
Copyright (C) 2020 Huawei Technologies Co., Ltd. All rights reserved.
*/
module huawei-fwd-engine {
  yang-version 1;
  namespace "urn:huawei:yang:huawei-fwd-engine";
  prefix fwd-engine;
  import huawei-extension {
    prefix ext;
  }
  import huawei-devm {
    prefix devm;
  }
  organization
    "Huawei Technologies Co., Ltd.";
  contact
    "Huawei Industrial Base
    Bantian, Longgang
    Shenzhen 518129
    People's Republic of China
    Website: http://www.huawei.com
    Email: support@huawei.com";
  description
    "Global Configuration.";
  revision 2020-03-09 {
    description
      "Initial revision.";
    reference
      "Huawei private.";
  }

  ext:task-name "device-mgr";

  augment "/devm:devm" {
    description
      "Forward engine configuration.";
    container fwd-performance-alarms {
      description
        "List of forwarding performance alarm.";
      list fwd-performance-alarm {
        key "slot-id";
        description
          "Configure the alarm reporting and alarm clearance thresholds for forwarding performance.";
        ext:generated-by system;
        ext:operation-exclude create|delete;
        leaf slot-id {
          type string {
            length "1..15";
          }
            description
              "Slot ID.";
        }
        leaf report-threshold {
          type uint32 {
            range "0..100";
          }
          units "%";
          must "(../report-threshold>../clear-threshold)";
          default "80";
          description
            "Specifies the alarm reporting threshold.";
        }
        leaf clear-threshold {
          type uint32 {
            range "0..100";
          }
          units "%";
          must "(../report-threshold>../clear-threshold)";
          default "75";
          description
            "Specifies the alarm clearance threshold.";
        }
      }
    }

    container fwd-services-alarms {
      description
        "List of value-added services alarm.";
      list fwd-services-alarm {
        key "slot-id";
        description
          "Configure the alarm reporting and alarm clearance thresholds for value-added services.";
        ext:generated-by system;
        ext:operation-exclude create|delete;
        leaf slot-id {
          type string {
            length "1..15";
          }
            description
              "Slot ID.";
        }
        leaf report-threshold {
          type uint32 {
            range "0..100";
          }
          units "%";
          must "(../report-threshold>../clear-threshold)";
          default "80";
          description
            "Specifies the alarm reporting threshold.";
        }
        leaf clear-threshold {
          type uint32 {
            range "0..100";
          }
          units "%";
          must "(../report-threshold>../clear-threshold)";
          default "75";
          description
            "Specifies the alarm clearance threshold.";
        }
      }
    }

    container fwd-reassembly-alarms {
      description
        "List of packet reassembly alarm.";
      list fwd-reassembly-alarm {
        key "slot-id";
        description
          "Configure the alarm reporting and alarm clearance thresholds for packet reassembly.";
        ext:generated-by system;
        ext:operation-exclude create|delete;
        leaf slot-id {
          type string {
            length "1..15";
          }
            description
              "Slot ID.";
        }
        leaf report-threshold {
          type uint32 {
            range "0..100";
          }
          units "%";
          must "(../report-threshold>../clear-threshold)";
          default "80";
          description
            "Specifies the alarm reporting threshold.";
        }
        leaf clear-threshold {
          type uint32 {
            range "0..100";
          }
          units "%";
          must "(../report-threshold>../clear-threshold)";
          default "75";
          description
            "Specifies the alarm clearance threshold.";
        }
      }
    }

    container fwd-board-flow-alarms {
      description
        "List of traffic alarm on a board.";
      list fwd-board-flow-alarm {
        key "slot-id";
        description
          "Configure the alarm reporting and alarm clearance thresholds for traffic on a board.";
        ext:generated-by system;
        ext:operation-exclude create|delete;
        leaf slot-id {
          type string {
            length "1..15";
          }
            description
              "Slot ID.";
        }
        leaf input-report-threshold {
          type uint32 {
            range "0..100";
          }
          units "%";
          must "(../input-report-threshold>../input-clear-threshold)";
          default "80";
          description
            "Specifies the input bandwidth alarm reporting threshold.";
        }
        leaf input-clear-threshold {
          type uint32 {
            range "0..100";
          }
          units "%";
          must "(../input-report-threshold>../input-clear-threshold)";
          default "75";
          description
            "Specifies the input bandwidth alarm clearance threshold.";
        }
        leaf output-report-threshold {
          type uint32 {
            range "0..100";
          }
          units "%";
          must "(../output-report-threshold>../output-clear-threshold)";
          default "80";
          description
            "Specifies the output bandwidth alarm reporting threshold.";
        }
        leaf output-clear-threshold {
          type uint32 {
            range "0..100";
          }
          units "%";
          must "(../output-report-threshold>../output-clear-threshold)";
          default "75";
          description
            "Specifies the output bandwidth alarm clearance threshold.";
        }
      }
    }
  }
}
