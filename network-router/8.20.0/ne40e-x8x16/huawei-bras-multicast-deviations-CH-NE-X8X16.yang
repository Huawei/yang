/*
Copyright (C) 2019 Huawei Technologies Co., Ltd. All rights reserved.
*/
module huawei-bras-multicast-deviations-CH-NE-X8X16 {
  namespace "urn:huawei:yang:huawei-bras-multicast-deviations-CH-NE-X8X16";
  prefix bras-multicast-devs-CH-NE-X8X16;

  import huawei-bras-multicast {
    prefix bras-multicast;
  }

  import huawei-devm {
    prefix devm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-multicast module.";

  revision 2019-11-06 {
    description
      "Initial revision.";
    reference
      "Huawei private.";
  }

  deviation "/devm:devm/devm:mpu-boards/devm:mpu-board/bras-basic-access:bras/bras-multicast:multicast" {
    deviate not-supported;
  }

}
