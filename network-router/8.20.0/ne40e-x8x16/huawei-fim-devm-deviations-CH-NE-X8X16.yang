/*
Copyright (C) 2019 Huawei Technologies Co., Ltd. All rights reserved.
*/
module huawei-fim-devm-deviations-CH-NE-X8X16 {
  namespace "urn:huawei:yang:huawei-fim-devm-deviations-CH-NE-X8X16";
  prefix fim-devm-devs-CH-NE-X8X16;

  import huawei-fim-devm {
    prefix fim-devm;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-fim-devm module.";

  revision 2019-11-06 {
    description
      "Initial revision.";
    reference
      "Huawei private.";
  }

  deviation "/devm:devm/devm:mpu-boards/devm:mpu-board/fim-devm:fim" {
    deviate not-supported;
  }
  deviation "/devm:devm/devm:mpu-boards/devm:mpu-board/fim-devm:macmtu-discard-statistics" {
    deviate not-supported;
  }
  deviation "/devm:devm/devm:mpu-boards/devm:mpu-board/fim-devm:ve-mac-address" {
    deviate not-supported;
  }

}
