/*
Copyright (C) 2020 Huawei Technologies Co., Ltd. All rights reserved.
*/
module huawei-evpl-deviations-NE-X1X2 {
  yang-version 1;
  namespace "urn:huawei:yang:huawei-evpl-deviations-NE-X1X2";
  prefix evpl-devs-NE-X1X2;

  import huawei-evpl {
    prefix evpl;
  }

  organization
    "Huawei Technologies Co., Ltd.";
  contact
    "Huawei Industrial Base
     Bantian, Longgang
     Shenzhen 518129
     People's Republic of China
     Website: http://www.huawei.com
     Email: support@huawei.com";
  description
    "Management of EVPL.";

  revision 2020-02-15 {
    description
      "Init revision.";
    reference "Huawei private.";
  }

  deviation "/evpl:evpl/evpl:instances/evpl:instance/evpl:evpl-statistics" {
    deviate not-supported;
  }
}
