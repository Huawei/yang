/*
Copyright (C) 2019 Huawei Technologies Co., Ltd. All rights reserved.
*/
module huawei-ppp-net {
  namespace "urn:huawei:yang:huawei-ppp-net";
  prefix ppp-net;
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "PPP net.";
  revision 2019-04-11 {
    description
      "Initial revision.";
    reference
      "Huawei private.";
  }
  ext:task-name "ppp";
  typedef ppp-damp-level-type {
    type enumeration {
      enum "light" {
        value "0";
        description
          "Light weight.";
      }
      enum "middle" {
        value "1";
        description
          "Middle weight.";
      }
      enum "heavy" {
        value "2";
        description
          "Heavy weight.";
      }
      enum "manual" {
        value "3";
        description
          "Manually configure the parameters.";
      }
    }
    description
      "PPP damp level type is light/middle/heavy/manual.";
  }
  container ppp-net {
    description
      "PPP net.";
    container ppp-dampening {
      presence "PPP protocol status damping enable.";
      description
        "Enable/disable type of PPP damp. If dampen-level is set to manual, the settings of the other parameters need to meet the following requirement: suppress-value/1000 <= (reuse-value/1000) * 2^ (max-suppress-time/half-life-period).";
      ext:generated-by system {
        ext:can-be-deleted;
        description "The ppp dampening whose level is light is generated by system automatically.";
      }
      leaf dampen-level {
        type ppp-damp-level-type;
        default "light";
        description
          "PPP protocol status damping level.";
      }
      leaf half-life-period {
        when "../dampen-level='manual'";
        type uint8 {
          range "1..60";
        }
        units s;
        mandatory true;
        description
          "PPP protocol status damping half life time (seconds)";
      }
      leaf suppress-value {
        when "../dampen-level='manual'";
        type uint16 {
          range "1..20000";
        }
        must "../suppress-value >= ../reuse-value";
        mandatory true;
        description
          "1000 times of PPP protocol status damping suppress threshold.";
      }
      leaf reuse-value {
        when "../dampen-level='manual'";
        type uint16 {
          range "1..20000";
        }
        must "../suppress-value >= ../reuse-value";
        mandatory true;
        description
          "1000 times of PPP protocol status damping reuse threshold.";
      }
      leaf max-suppress-time {
        when "../dampen-level='manual'";
        type uint8 {
          range "1..255";
        }
        units s;
        mandatory true;
        description
          "PPP protocol status damping max suppress time (seconds)";
      }
    }
  }
}
