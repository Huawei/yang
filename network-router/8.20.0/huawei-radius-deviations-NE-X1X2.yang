/*
Copyright (C) 2019 Huawei Technologies Co., Ltd. All rights reserved.
*/
module huawei-radius-deviations-NE-X1X2 {
  namespace "urn:huawei:yang:huawei-radius-deviations-NE-X1X2";
  prefix radius-devs-NE-X1X2;

  import huawei-radius {
    prefix radius;
  }

  organization
    "Huawei Technologies Co., Ltd.";

  contact
    "Huawei Industrial Base
     Bantian, Longgang
     Shenzhen 518129
     People's Republic of China
     Website: http://www.huawei.com
     Email: support@huawei.com";

  description
    "This module defines deviation statements for huawei-radius module.";

  revision 2019-11-06 {
    description
      "Initial revision.";
    reference
      "Huawei private.";
  }

  deviation "/radius:radius/radius:radius-server-groups/radius:radius-server-group/radius:authen-account-attribute/radius:cmcc-up-identifier" {
    deviate not-supported;
  }
  deviation "/radius:radius/radius:radius-server-groups/radius:radius-server-group/radius:authen-account-attribute/radius:cmcc-up-ip" {
    deviate not-supported;
  }
  deviation "/radius:radius/radius:radius-server-groups/radius:radius-server-group/radius:bod-account-attribute" {
    deviate not-supported;
  }

}
