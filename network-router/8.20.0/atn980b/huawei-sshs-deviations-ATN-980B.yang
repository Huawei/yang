/*
Copyright (C) 2019 Huawei Technologies Co., Ltd. All rights reserved.
*/
module huawei-sshs-deviations-ATN-980B {
  namespace "urn:huawei:yang:huawei-sshs-deviations-ATN-980B";
  prefix sshs-devs-ATN-980B;

  import huawei-sshs {
    prefix sshs;
  }
  import huawei-sm2 {
    prefix sm2;
  }

  organization
    "Huawei Technologies Co., Ltd.";
  contact
    "Huawei Industrial Base
     Bantian, Longgang
     Shenzhen 518129
     People's Republic of China
     Website: http://www.huawei.com
     Email: support@huawei.com";
  description
    "Sshs management.";

  revision 2019-05-01 {
    description
      "Initial revision.";
    reference "Huawei private.";
  }

  typedef sshs-user-auth-deviations {
    type enumeration {
      enum not-set {
        value 0;
        description
          "The user authentication type is not set.";
      }
      enum password {
        value 1;
        description
          "User authentication type password.";
      }
      enum rsa {
        value 2;
        description
          "User authentication type RSA.";
      }
      enum all {
        value 3;
        description
          "User authentication type all.";
      }
      enum password-rsa {
        value 4;
        description
          "User authentication type password RSA.";
      }
      enum dsa {
        value 5;
        description
          "User authentication type DSA.";
      }
      enum password-dsa {
        value 6;
        description
          "User authentication type password DSA.";
      }
      enum ecc {
        value 7;
        description
          "User authentication type ECC.";
      }
      enum password-ecc {
        value 8;
        description
          "User authentication type password ECC.";
      }
    }
    description
      "SSH server user authentication type list.";
  }

  typedef sshs-user-pubkey-type-deviations {
    type enumeration {
      enum not-set {
        value 0;
        description
          "Server public key is not set.";
      }
      enum RSA {
        value 1;
        description
          "RSA server public key.";
      }
      enum DSA {
        value 2;
        description
          "DSA server public key.";
      }
      enum ECC {
        value 3;
        description
          "ECC server public key.";
      }
    }
    description
      "SSH server public key encryption type list for user.";
  }

  deviation "/sshs:sshs/sshs:users/sshs:user/sshs:auth-type" {
    deviate replace {
      type sshs-devs-ATN-980B:sshs-user-auth-deviations;
    }
  }
  deviation "/sshs:sshs/sshs:users/sshs:user/sshs:pub-key-type" {
    deviate replace {
      type sshs-devs-ATN-980B:sshs-user-pubkey-type-deviations;
    }
  }
  deviation "/sshs:sshs/sshs:session-car/sshs:cir-interval" {
    deviate replace {
      units "pps";
      default "800";
    }
  }
  deviation "/sshs:sshs/sshs:session-car/sshs:cbs-interval" {
    deviate replace {
      units "packet";
      default "3600";
    }
  }
  deviation "/sshs:sshs/sshs:session-car/sshs:pir-interval" {
    deviate replace {
      units "pps";
      default "32000";
    }
  }
  deviation "/sshs:sshs/sshs:session-car/sshs:pbs-interval" {
    deviate replace {
      units "packet";
      default "72000";
    }
  }
  deviation "/sshs:sshs/sshs:server/sshs:pki-domain" {
    deviate not-supported;
  }
  deviation "/sshs:sshs/sshs:pubkey-alg" {
    deviate delete {
      must "../pubkey-alg/dsa = 'true' or ../pubkey-alg/ecc = 'true' or ../pubkey-alg/rsa = 'true' or ../pubkey-alg/sm2 = 'true' or ../pubkey-alg/x509v3-ssh-rsa = 'true' or ../pubkey-alg/rsa-sha2-256 = 'true' or ../pubkey-alg/rsa-sha2-512 = 'true'";
    }
    deviate add {
      must "../pubkey-alg/dsa = 'true' or ../pubkey-alg/ecc = 'true' or ../pubkey-alg/rsa = 'true' or ../pubkey-alg/rsa-sha2-256 = 'true' or ../pubkey-alg/rsa-sha2-512 = 'true'";
    }
  }
  deviation "/sshs:sshs/sshs:pubkey-alg/sshs:x509v3-ssh-rsa" {
    deviate not-supported;
  }
  deviation "/sshs:sshs/sshs:pubkey-alg/sshs:sm2" {
    deviate not-supported;
  }
  deviation "/sshs:sshs/sshs:users/sshs:user/sshs:key-name" {
    deviate delete {
      must "../pub-key-type = 'RSA' or ../pub-key-type = 'SM2' or ../pub-key-type = 'DSA' or ../pub-key-type = 'ECC'";
    }
    deviate add {
      must "../pub-key-type = 'RSA' or ../pub-key-type = 'DSA' or ../pub-key-type = 'ECC'";
    }
    deviate delete {
      must "(../pub-key-type = 'SM2' and ../key-name = /sm2:sm2/sm2:sm2-peer-keys/sm2:sm2-peer-key[sm2:key-name=current()]/sm2:key-name) or ../pub-key-type != 'SM2'";
    }
  }
  deviation "/sshs:sshs/sshs:server/sshs:sm2-host-key" {
    deviate not-supported;
  }
}
