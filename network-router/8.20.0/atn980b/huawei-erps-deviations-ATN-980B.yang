/*
Copyright (C) 2020 Huawei Technologies Co., Ltd. All rights reserved.
*/
module huawei-erps-deviations-ATN-980B {
  namespace "urn:huawei:yang:huawei-erps-deviations-ATN-980B";
  prefix erps-devs-ATN-980B;

  import huawei-erps {
    prefix erps;
  }

  organization
    "Huawei Technologies Co., Ltd.";
  contact
    "Huawei Industrial Base
     Bantian, Longgang
     Shenzhen 518129
     People's Republic of China
     Website: http://www.huawei.com
     Email: support@huawei.com";
  description
    "Link layer discovery protocol.";

  revision 2020-06-01 {
    description
      "Initial revision.";
    reference "Huawei private.";
  }

  deviation "/erps:erps/erps:rings/erps:ring/erps:description" {
    deviate not-supported;
  }
  deviation "/erps:erps/erps:rings/erps:ring/erps:wait-restore-timer" {
    deviate not-supported;
  }
  deviation "/erps:erps/erps:rings/erps:ring/erps:raps-mel" {
    deviate not-supported;
  }
  deviation "/erps:erps/erps:rings/erps:ring/erps:revertive-enable" {
    deviate not-supported;
  }
  deviation "/erps:erps/erps:rings/erps:ring/erps:tc-protection-interval" {
    deviate not-supported;
  }
  deviation "/erps:erps/erps:rings/erps:ring/erps:tc-protection-threshold" {
    deviate not-supported;
  }
  deviation "/erps:erps/erps:rings/erps:ring/erps:version-v2" {
    deviate not-supported;
  }
  deviation "/erps:erps/erps:rings/erps:ring/erps:port-attributes" {
    deviate not-supported;
  }
}
