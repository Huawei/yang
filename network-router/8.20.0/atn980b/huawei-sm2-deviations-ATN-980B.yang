/*
Copyright (C) 2019 Huawei Technologies Co., Ltd. All rights reserved.
*/
module huawei-sm2-deviations-ATN-980B {
  namespace "urn:huawei:yang:huawei-sm2-deviations-ATN-980B";
  prefix sm2-devs-ATN-980B;

  import huawei-sm2 {
    prefix sm2;
  }

  organization
    "Huawei Technologies Co., Ltd.";
  contact
    "Huawei Industrial Base
     Bantian, Longgang
     Shenzhen 518129
     People's Republic of China
     Website: http://www.huawei.com
     Email: support@huawei.com";
  description
    "SM2.";

  revision 2019-05-01 {
    description
      "Initial revision.";
    reference "Huawei private.";
  }

  deviation "/sm2:sm2" {
    deviate not-supported;
  }
}
