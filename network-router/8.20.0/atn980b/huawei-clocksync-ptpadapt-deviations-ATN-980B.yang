/*
Copyright (C) 2019 Huawei Technologies Co., Ltd. All rights reserved.
*/
module huawei-clocksync-ptpadapt-deviations-ATN-980B {
  namespace "urn:huawei:yang:huawei-clocksync-ptpadapt-deviations-ATN-980B";
  prefix "clocksync-ptpadapt-devs-ATN-980B";

  import huawei-clocksync-ptpadapt {
    prefix "clocksync-ptpadapt";
  }
  organization
    "Huawei Technologies Co., Ltd.";
  contact
    "Huawei Industrial Base
     Bantian, Longgang
     Shenzhen 518129
     People's Republic of China
     Website: http://www.huawei.com
     Email: support@huawei.com";
  description
    "System clock synchronization management, including frequency synchronization and time synchronization.";
  revision 2019-07-08 {
    description
      "Init revision.";
    reference
      "Huawei private.";
  }
 
  deviation /clocksync-ptpadapt:clocksync-ptpadapt/clocksync-ptpadapt:ptpa-common/clocksync-ptpadapt:hop-by-hop-mode {
	deviate not-supported;
  }

}
