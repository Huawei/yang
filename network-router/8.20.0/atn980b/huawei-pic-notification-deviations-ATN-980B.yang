/*
Copyright (C) 2019 Huawei Technologies Co., Ltd. All rights reserved.
*/
module huawei-pic-notification-deviations-ATN-980B {
  namespace "urn:huawei:yang:huawei-pic-notification-deviations-ATN-980B";
  prefix pic-notification-devs-ATN-980B;

  import huawei-pic-notification {
    prefix pic-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic-notification module.";

  revision 2019-11-06 {
    description
      "Initial revision.";
    reference
      "Huawei private.";
  }

  deviation "/pic-notification:flow-control-pause-frame-abnormal" {
    deviate not-supported;
  }
  deviation "/pic-notification:flow-control-pause-frame-abnormal-resume" {
    deviate not-supported;
  }
  deviation "/pic-notification:remote-e3" {
    deviate not-supported;
  }
  deviation "/pic-notification:remote-e3-resume" {
    deviate not-supported;
  }
  deviation "/pic-notification:upstream-e3" {
    deviate not-supported;
  }
  deviation "/pic-notification:upstream-e3-resume" {
    deviate not-supported;
  }
  deviation "/pic-notification:resource-dead-line" {
    deviate not-supported;
  }
  deviation "/pic-notification:resource-dead-line-resume" {
    deviate not-supported;
  }
  deviation "/pic-notification:upstream-pcm" {
    deviate not-supported;
  }
  deviation "/pic-notification:upstream-pcm-resume" {
    deviate not-supported;
  }
  deviation "/pic-notification:fog-abnormal" {
    deviate not-supported;
  }
  deviation "/pic-notification:fog-abnormal-resume" {
    deviate not-supported;
  }
  deviation "/pic-notification:gate-abnormal" {
    deviate not-supported;
  }
  deviation "/pic-notification:gate-abnormal-resume" {
    deviate not-supported;
  }
  deviation "/pic-notification:trace-unstable-lp" {
    deviate not-supported;
  }
  deviation "/pic-notification:trace-unstable-lp-resume" {
    deviate not-supported;
  }
  deviation "/pic-notification:humidity-abnormal" {
    deviate not-supported;
  }
  deviation "/pic-notification:humidity-abnormal-resume" {
    deviate not-supported;
  }
  deviation "/pic-notification:bad-bytes-error-rising" {
    deviate not-supported;
  }
  deviation "/pic-notification:bad-bytes-error-resume" {
    deviate not-supported;
  }
  deviation "/pic-notification:post-fec-error-rising" {
    deviate not-supported;
  }
  deviation "/pic-notification:post-fec-error-resume" {
    deviate not-supported;
  }
  deviation "/pic-notification:sdh-b2-error-rising" {
    deviate not-supported;
  }
  deviation "/pic-notification:sdh-b2-error-resume" {
    deviate not-supported;
  }
  deviation "/pic-notification:sdh-error-rising" {
    deviate not-supported;
  }
  deviation "/pic-notification:sdh-error-resume" {
    deviate not-supported;
  }
  deviation "/pic-notification:symbol-error-interval" {
    deviate not-supported;
  }
  deviation "/pic-notification:symbol-error-interval-resume" {
    deviate not-supported;
  }
  deviation "/pic-notification:tx-pause-frame-exceed" {
    deviate not-supported;
  }
  deviation "/pic-notification:tx-pause-frame-exceed-resume" {
    deviate not-supported;
  }
  deviation "/pic-notification:input-error-exceed" {
    deviate not-supported;
  }
  deviation "/pic-notification:input-error-exceed-resume" {
    deviate not-supported;
  }
  deviation "/pic-notification:laser-no-fited" {
    deviate not-supported;
  }
  deviation "/pic-notification:laser-no-fited-resume" {
    deviate not-supported;
  }
  deviation "/pic-notification:laser-shut" {
    deviate not-supported;
  }
  deviation "/pic-notification:laser-shut-resume" {
    deviate not-supported;
  }
  deviation "/pic-notification:odu-signal-degrade" {
    deviate not-supported;
  }
  deviation "/pic-notification:otu-signal-degrade" {
    deviate not-supported;
  }
  deviation "/pic-notification:otu-signal-degrade-resume" {
    deviate not-supported;
  }
  deviation "/pic-notification:otu-signal-fail" {
    deviate not-supported;
  }
  deviation "/pic-notification:otu-signal-fail-resume" {
    deviate not-supported;
  }
  deviation "/pic-notification:output-error-exceed" {
    deviate not-supported;
  }
  deviation "/pic-notification:output-error-exceed-resume" {
    deviate not-supported;
  }
  deviation "/pic-notification:crc-error-warning" {
    deviate not-supported;
  }
  deviation "/pic-notification:crc-error-warning-resume" {
    deviate not-supported;
  }
  deviation "/pic-notification:trans-mode-inconsistent" {
    deviate not-supported;
  }
  deviation "/pic-notification:trans-mode-inconsistent-resume" {
    deviate not-supported;
  }
  deviation "/pic-notification:port-mode-change" {
    deviate not-supported;
  }
  deviation "/pic-notification:port-physical-down" {
    deviate not-supported;
  }
  deviation "/pic-notification:port-physical-up" {
    deviate not-supported;
  }
  deviation "/pic-notification:physical-rate-degrade" {
    deviate not-supported;
  }
  deviation "/pic-notification:physical-rate-degrade-resume" {
    deviate not-supported;
  }
  deviation "/pic-notification:port-type-change" {
    deviate not-supported;
  }
  deviation "/pic-notification:remote-defect" {
    deviate not-supported;
  }
  deviation "/pic-notification:remote-defect-resume" {
    deviate not-supported;
  }
  deviation "/pic-notification:license-resource-lack" {
    deviate not-supported;
  }
  deviation "/pic-notification:license-resource-lack-resume" {
    deviate not-supported;
  }
  deviation "/pic-notification:optical-unauthorized" {
    deviate not-supported;
  }
  deviation "/pic-notification:optical-unauthorized-resume" {
    deviate not-supported;
  }
}
