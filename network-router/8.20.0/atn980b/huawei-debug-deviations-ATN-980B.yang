/*
Copyright (C) 2019 Huawei Technologies Co., Ltd. All rights reserved.
*/
module huawei-debug-deviations-ATN-980B {
  namespace "urn:huawei:yang:huawei-debug-deviations-ATN-980B";
  prefix debug-devs-ATN-980B;

  import huawei-debug {
    prefix debug;
  }

  organization
    "Huawei Technologies Co., Ltd.";
  contact
    "Huawei Industrial Base
     Bantian, Longgang
     Shenzhen 518129
     People's Republic of China
     Website: http://www.huawei.com
     Email: support@huawei.com";
  description
    "Debug management.";

  revision 2019-04-10 {
    description
      "Init revision.";
    reference "Huawei private.";
  }

  deviation "/debug:debug/debug:memory-infos/debug:memory-info" {
    deviate delete {
      must 'overload-threshold <= memreli-overload-threshold';
    }
  }
  deviation "/debug:debug/debug:memory-infos/debug:memory-info" {
    deviate delete {
      must 'memreli-notice-threshold < memreli-overload-threshold';
    }
  }
  deviation "/debug:debug/debug:memory-infos/debug:memory-info/debug:memreli-notice-threshold" {
    deviate not-supported;
  }
  deviation "/debug:debug/debug:memory-infos/debug:memory-info/debug:memreli-overload-threshold" {
    deviate not-supported;
  }
  deviation "/debug:debug/debug:resouce-reliability/debug:memory-reliability" {
    deviate not-supported;
  }
  deviation "/debug:debug/debug:resouce-reliability/debug:memory-reliability-switchover-threshold" {
    deviate not-supported;
  }
}
