/*
Copyright (C) 2019 Huawei Technologies Co., Ltd. All rights reserved.
*/
module huawei-bgp-evpn-deviations-ATN-980B {
  namespace "urn:huawei:yang:huawei-bgp-evpn-deviations-ATN-980B";
  prefix bgp-evpn-devs-ATN-980B;

  import huawei-bgp {
    prefix bgp;
  }
  import huawei-network-instance {
    prefix ni;
  }
  import huawei-bgp-evpn {
    prefix bgp-evpn;
  }

  organization
    "Huawei Technologies Co., Ltd.";
  contact
    "Huawei Industrial Base
     Bantian, Longgang
     Shenzhen 518129
     People's Republic of China
     Website: http://www.huawei.com
     Email: support@huawei.com";
  description
    "BGP EVPN configuration.";

  revision 2019-03-22 {
    description
      "Initial revision.";
    reference "Huawei private.";
  }

  deviation "/ni:network-instance/ni:instances/ni:instance/bgp:bgp/bgp:base-process/bgp:afs/bgp:af/bgp-evpn:l2vpn-evpn/bgp-evpn:add-path-select-num" {
    deviate replace {
      type uint8 {
        range "2..64";
      }
    }
  }
  deviation "/ni:network-instance/ni:instances/ni:instance/bgp:bgp/bgp:base-process/bgp:afs/bgp:af/bgp-evpn:l2vpn-evpn/bgp-evpn:rr-ext-community-filter" {
    deviate not-supported;
  }
  deviation "/ni:network-instance/ni:instances/ni:instance/bgp:bgp/bgp:base-process/bgp:peer-groups/bgp:peer-group/bgp:afs/bgp:af/bgp-evpn:l2vpn-evpn/bgp-evpn:advertise-add-path-num" {
    deviate replace {
      type uint8 {
        range "2..64";
      }
    }
  }
  deviation "/ni:network-instance/ni:instances/ni:instance/bgp:bgp/bgp:base-process/bgp:peers/bgp:peer/bgp:afs/bgp:af/bgp-evpn:l2vpn-evpn/bgp-evpn:advertise-add-path-num" {
    deviate replace {
      type uint8 {
        range "2..64";
      }
    }
  }
  deviation "/ni:network-instance/ni:instances/ni:instance/bgp:bgp/bgp:base-process/bgp:afs/bgp:af/bgp:ipv4-unicast/bgp-evpn:evpn/bgp-evpn:irb-asymmetric/bgp-evpn:policy-name" {
    deviate not-supported;
  }
  deviation "/ni:network-instance/ni:instances/ni:instance/bgp:bgp/bgp:base-process/bgp:afs/bgp:af/bgp:ipv6-unicast/bgp-evpn:evpn/bgp-evpn:irb-asymmetric/bgp-evpn:policy-name" {
    deviate not-supported;
  }
}
