/*
Copyright (C) 2019 Huawei Technologies Co., Ltd. All rights reserved.
*/
module huawei-y1731 {
  namespace "urn:huawei:yang:huawei-y1731";
  prefix y1731;
  import huawei-ifm {
    prefix ifm;
  }
  import huawei-l2vpn {
    prefix l2vpn;
  }
  import huawei-pub-type {
    prefix pub-type;
  }
  import ietf-inet-types {
    prefix inet;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "Y.1731 is developed by ITU-T for operations, administration and maintenance (OAM) of Ethernet, which providing fault management and performance management solutions for Ethernet.";
  revision 2019-12-10 {
    description
      "Initial revision.";
    reference
      "Huawei private.";
  }
  ext:task-name  "y1731"; 
  typedef version {
    type enumeration {
      enum "draft7" {
        value 0;
        description
          "IEEE 802.1ag draft 7.";
      }
      enum "standard" {
        value 1;
        description
          "IEEE std 802.1ag-2007.";
      }
    }
    description
      "CFM version.";
  }
  typedef mp-address-model {
    type enumeration {
      enum "bridge" {
        value 1;
        description
          "Bridge MAC model of an 802.1ag protocol.";
      }
      enum "individual" {
        value 2;
        description
          "Individual MAC model of an 802.1ag protocol.";
      }
    }
    description
      "MP address model.";
  }
  typedef portid-tlv-type {
    type enumeration {
      enum "interface-name" {
        value 5;
        description
          "Interface name type of port ID TLV.";
      }
      enum "local" {
        value 7;
        description
          "Private type of port ID TLV.";
      }
    }
    description
      "Port ID TLV type.";
  }
  typedef ccm-interval {
    type enumeration {
      enum "3.3ms" {
        value 1;
        description
          "CCM interval of 3.3 ms.";
      }
      enum "10ms" {
        value 2;
        description
          "CCM interval of 10 ms.";
      }
      enum "20ms" {
        value 8;
        description
          "CCM interval of 20 ms.";
      }
      enum "30ms" {
        value 9;
        description
          "CCM interval of 30 ms.";
      }
      enum "50ms" {
        value 10;
        description
          "CCM interval of 50 ms.";
      }
      enum "100ms" {
        value 3;
        description
          "CCM interval of 100 ms.";
      }
      enum "1s" {
        value 4;
        description
          "CCM interval of 1s.";
      }
      enum "10s" {
        value 5;
        description
          "CCM interval of 10s.";
      }
      enum "1min" {
        value 6;
        description
          "CCM interval of 1 min.";
      }
      enum "10min" {
        value 7;
        description
          "CCM interval of 10 min.";
      }
    }
    description
      "CCM interval.";
  }
  typedef l2vc-type {
    type enumeration {
      enum "vlan" {
        value 4;
        description
          "Configure the L2VPN encapsulation type as VLAN.";
      }
      enum "ethernet" {
        value 5;
        description
          "Configure the L2VPN encapsulation type as Ethernet.";
      }
    }
    description
      "L2VC type.";
  }
  typedef ma-format {
    type enumeration {
      enum "string" {
        value 2;
        description
          "The maintenance association's name is in string format.";
      }
      enum "icc-based" {
        value 32;
        description
          "The maintenance association's name is in ICC-based format.";
      }
    }
    description
      "MD format type.";
  }
  typedef md-format {
    type enumeration {
      enum "none" {
        value 1;
        description
          "CCM packets have no maintenance domain name.";
      }
      enum "dns" {
        value 2;
        description
          "The maintenance domain name is CCM packets DNS name.";
      }
      enum "mac-address" {
        value 3;
        description
          "The maintenance domain name is MAC and 2-octet integer (H-H-H:U<0-65535>, example: 0001-0001-0001:1).";
      }
      enum "string" {
        value 4;
        description
          "The maintenance domain name is string format.";
      }
    }
    description
      "MA format type.";
  }
  typedef mip-create-type {
    type enumeration {
      enum "default" {
        value 2;
        description
          "The rule of default: MIPs can be created on the port of the MD only when the port does not have the MEP of a higher MD-level or the MIP of a lower MD-level.";
      }
      enum "explicit" {
        value 1;
        description
          "The rule of explicit: MIPs can be created on the port of the MD only when the port meets the following conditions: The port does not have the MEP of a higher MD-level or the MIP of a lower MD-level; The port has the MEP of a lower MD-level.";
      }
      enum "none" {
        value 0;
        description
          "The rule of none: No MIPs can be created on the port of the maintenance domain.";
      }
    }
    description
      "MIP create type.";
  }
  typedef sender-tlv-type {
    type enumeration {
      enum "none" {
        value 1;
        description
          "The sender ID TLV is not to be sent.";
      }
      enum "chassis" {
        value 2;
        description
          "Information about the chassis ID is to be sent.";
      }
      enum "manage" {
        value 3;
        description
          "Information about the management address is to be sent.";
      }
      enum "chassis-manage" {
        value 4;
        description
          "Information about the chassis ID and management address is to be sent.";
      }
      enum "defer" {
        value 5;
        description
          "The contents are determined by the maintenance domain managed object.";
      }
    }
    description
      "Sender TLV type.";
  }
  typedef ma-mip-create-type {
    type enumeration {
      enum "default" {
        value 2;
        description
          "The rule of default: MIPs can be created on the port of the MA only when the port does not have the MEP of a higher MD-level or the MIP of a lower MD-level.";
      }
      enum "explicit" {
        value 1;
        description
          "The rule of explicit: MIPs can be created on the port of the MA only when the port meets the following conditions: The port does not have the MEP of a higher MD-level or the MIP of a lower MD-level; The port has the MEP of a lower MD-level.";
      }
      enum "none" {
        value 0;
        description
          "The rule of none: No MIPs can be created on the port of the maintenance association.";
      }
      enum "defer" {
        value 3;
        description
          "The rule of defer: The rule of MIP creation is deferred to the corresponding variable in the enclosing maintenance domain.";
      }
    }
    description
      "MA mip create type.";
  }
  typedef ais-interval {
    type enumeration {
      enum "1s" {
        value 1;
        description
          "AIS interval of 1s.";
      }
      enum "60s" {
        value 60;
        description
          "AIS interval of 60s.";
      }
    }
    description
      "AIS interval.";
  }
  typedef direction {
    type enumeration {
      enum "inward" {
        value 0;
        description
          "Type of a MEP, which sends packets to the device's relay.";
      }
      enum "outward" {
        value 1;
        description
          "Type of a MEP, which sends packets out of device.";
      }
    }
    description
      "MEP direction.";
  }
  typedef alarm-type {
    type enumeration {
      enum "unexpected-meg-level" {
        value 0;
        description
          "The MEG level of CCM packets is unexpected which the MEP received.";
      }
      enum "unexpected-mep" {
        value 2;
        description
          "The MEP ID of CCM packets is unexpected which the MEP received.";
      }
      enum "mismerge" {
        value 1;
        description
          "The MEG ID of CCM packets is unexpected which the MEP received.";
      }
      enum "unexpected-period" {
        value 3;
        description
          "The interval of CCM packets is unexpected which the MEP received.";
      }
      enum "unexpected-mac" {
        value 4;
        description
          "The resource MAC of CCM packets is unexpected which the MEP received.";
      }
      enum "LOC" {
        value 5;
        description
          "Fault of lost connection.";
      }
      enum "exceptional-mac-status" {
        value 6;
        description
          "The value of interface status TLV is not up.";
      }
      enum "RDI" {
        value 7;
        description
          "Fault of remote defect indication.";
      }
      enum "none" {
        value 254;
        description
          "There is no fault.";
      }
    }
    description
      "Alarm type.";
  }
  typedef sslm-interval {
    type enumeration {
      enum "3.3ms" {
        value 3;
        description
          "Interval of 3.3 ms.";
      }
      enum "10ms" {
        value 10;
        description
          "Interval of 10 ms.";
      }
      enum "100ms" {
        value 100;
        description
          "Interval of 100 ms.";
      }
      enum "1000ms" {
        value 1000;
        description
          "Interval of 1000 ms.";
      }
      enum "10000ms" {
        value 10000;
        description
          "Interval of 10000 ms.";
      }
    }
    description
      "SSLM interval.";
  }
  typedef interval {
    type enumeration {
      enum "1000ms" {
        value 1000;
        description
          "Interval of 1000 ms.";
      }
      enum "10000ms" {
        value 10000;
        description
          "Interval of 10000 ms.";
      }
      enum "30000ms" {
        value 30000;
        description
          "Interval of 30000 ms.";
      }
      enum "60000ms" {
        value 60000;
        description
          "Interval of 60000 ms.";
      }
    }
    description
      "Y1731 message interval.";
  }
  container y1731 {
    description
      "Configure Y.1731 attributes. Y.1731 is developed by ITU-T for operations, administration and maintenance (OAM) of Ethernet, which providing fault management and performance management solutions for Ethernet.";
    container global-attribute {
      description
        "Configure global Y.1731 attributes.";
      leaf cfm-version {
        type version;
        default "standard";
        description
          "Version of Y.1731, which can be standard or draft7.";
      }
      leaf mp-address-model {
        type mp-address-model;
        default "bridge";
        description
          "MAC model of Y.1731, which can be bridge or individual.";
      }
      leaf pm-mode-enable {
        type boolean;
        default "false";
        description
          "Enable/disable Y.1731 PM.";
      }
      leaf portid-tlv {
        type portid-tlv-type;
        default "interface-name";
        description
          "Set the type of port ID TLV in MAC trace packet.";
      }
      leaf idle-test-id-count {
        type uint16;
        default "1";
        description
          "Set the number of idle test ID for query.";
      }
    }
    container global-enable {
      when "(../global-attribute/cfm-version='standard')";
      presence "Enable/disable Y.1731.";
      description
        "Configure global-enable Y.1731 attributes. Y.1731 is developed by ITU-T for operations, administration and maintenance (OAM) of Ethernet, which providing fault management and performance management solutions for Ethernet.";
      container mds {
        description
          "List of all maintenance domains.";
        list md {
          key "name";
          description
            "Configure a maintenance domain.";
          leaf name {
            type string {
              length "1..43";
              pattern '[^\?]*';
            }
            description
              "Configure the name of a maintenance domain (MD).";
          }
          leaf level {
            ext:operation-exclude update|delete;
            type uint8 {
              range "0..7";
            }
            default "0";
            description
              "Configure the level of the maintenance domain.";
          }
          leaf format {
            ext:operation-exclude update|delete;
            type md-format;
            must "((../format='string') or ((../format='none') and (not(../format-name))) or ((../format!='none') and (../format-name)))";
            default "string";              
            description
              "Configure the format of the maintenance domain name. By default, the format is a string. If the format is MAC-address, the format name must be in form of H-H-H:U<0-65535>, for example, 0001-0001-0001:1.";
          }
          leaf format-name {
            ext:operation-exclude update|delete;
            when "../format!='none'";
            type string {
              length "1..43";
              pattern '[^\?]*';
            }
            ext:dynamic-default {
              ext:default-value "../name" {
                when "../format='string'";
                description "The default value equals to the value of name when the format is string.";
              }
            }
            description
              "Configure the name of the maintenance domain which will be formatted. By default, it is the same as the name of the maintenance domain.";
          }
          leaf mip-create-type {
            type mip-create-type;
            default "none";
            description
              "Configure the MIP create type of maintenance domain."; 
          }
          leaf sender-tlv-type {
            type sender-tlv-type;
            default "defer";
            description
              "Configure the sender ID TLV type of the default maintenance domain.";
          }
          container mas {
            description
              "List of all maintenance associations.";
            list ma {
              key "name";
              description
                "Configure a maintenance association.";
              leaf name {
                type string {
                  length "1..43";
                  pattern '[^\?]*';
                }
                description
                  "Configure the name of a maintenance association (MA).";
              }
              leaf format {
                ext:operation-exclude update|delete;
                type ma-format;
                must "((../format='icc-based' and ../../../format='none' and ../format-name) or (../format!='icc-based'))";
                default "string";
                description
                  "Configure the format of the maintenance association's name.";
              }
              leaf format-name {
                ext:operation-exclude update|delete;
                type string {
                  length "1..43";
                  pattern '[^\?]*';
                }
                ext:dynamic-default {
                  ext:default-value "../name" {
                    when "../format='string'";
                    description "The default value equals to the value of name when the format is string.";
                  }
                }
                description
                  "Configure the name of the maintenance association (MA) which will be formatted. By default, as the same with the name of the MA. The length of MA format description is [1,13] when the format is ICC-based, and [1,43] when it is string.";
              }
              choice map-service {
                default no-bind;
                description
                  "Configure the type of a maintenance association's service.";
                case no-bind {
                  description
                    "MA map no service.";
                  leaf no-bind {
                    type empty;
                    description
                      "MA map no service.";
                  }
                }
                case bind-vlan {
                  description
                    "Map a VLAN.";
                  leaf vlan-id {
                    ext:operation-exclude update {
                     when "../meps/mep or ../rmeps/rmep";
                       description "The value cannot be updated, when mep or rmep exists.";
                    }
                    type uint16 {
                      range "1..4094";
                    }
                    mandatory true;
                    description
                      "Configure the VLAN ID associated with the maintenance association.";
                  }
                  leaf one-way-threshold-value {
                    ext:operation-exclude update;
                    type uint32 {
                      range "1..4294967295";
                    }
                    units "ms";
                    description
                      "Configure the threshold of one-way delay measurement.";
                  }
                  leaf two-way-threshold-value {
                    ext:operation-exclude update;
                    type uint32 {
                      range "1..4294967295";
                    }
                    units "ms";
                    description
                      "Configure the threshold of two-way delay measurement.";
                  }
                }
                case bind-l2vc {
                  description
                    "Map a L2VC.";
                  leaf l2vc-id {
                    ext:operation-exclude update {
                     when "../meps/mep or ../rmeps/rmep";
                       description "The 'l2vc-id' cannot be updated, when mep or rmep exists.";
                    }
                    type leafref {
                      path "/l2vpn:l2vpn/l2vpn:instances/l2vpn:instance/l2vpn:vpws-ldp/l2vpn:pws/l2vpn:pw/l2vpn:pw-id";
                    }
                    must "count(../meps/mep)<=1";
                    mandatory true;
                    description
                     "Configure the ID of the L2VC associated with the maintenance association.";
                    ext:support-filter "true"; 
                  }
                  leaf l2vc-type {
                    ext:operation-exclude update {
                     when "../meps/mep or ../rmeps/rmep";
                       description "The 'l2vc-type' cannot be updated, when mep or rmep exists.";
                    }
                    type l2vc-type;
                    mandatory true;
                    description
                      "Configure the type of the L2VC associated with the maintenance association.";
                    ext:support-filter "true";
                  }
                  leaf l2vc-ip {
                    type leafref {
                      path "/l2vpn:l2vpn/l2vpn:instances/l2vpn:instance/l2vpn:vpws-ldp/l2vpn:pws/l2vpn:pw/l2vpn:peer-ip";
                    }           
                    description
                      "Configure the peer IP of the L2VC associated with the maintenance association.";
                  }
                }
                case bind-vsi {
                  description
                    "Map a VSI.";
                  leaf vsi-name {
                    ext:operation-exclude update {
                     when "../meps/mep or ../rmeps/rmep";
                       description "The 'vsi-name' cannot be updated, when mep or rmep exists.";
                    }
                    type leafref {
                      path "/l2vpn:l2vpn/l2vpn:instances/l2vpn:instance/l2vpn:name";
                    }
                    must "/l2vpn:l2vpn/l2vpn:instances/l2vpn:instance[l2vpn:name = current()][l2vpn:type='vpls']";
                    description
                      "Configure the name of the VSI associated with the maintenance association.";
                    ext:support-filter "true";
                  }
                }
              }
              leaf packet-priority {
                type uint8 {
                  range "0..7";
                }
                default "7";
                description
                  "Configure the priority of the packet which is sent in the maintenance association.";
              }
              leaf ccm-interval {
                type ccm-interval;
                default "1s";
                description
                  "Configure the interval at which CCMs are sent in a maintenance association.";
              }
              leaf alarm-occur-time {
                type uint16 {
                  range "0..30000";
                }
                units "ms";
                must "(../alarm-occur-time mod 500)=0";
                default "2500";
                description
                  "Configure the delay for reporting an alarm."; 
              }
              leaf alarm-finish-time {
                type uint16 {
                  range "0..30000";
                }
                units "ms";
                must "(../alarm-finish-time mod 500)=0";
                default "10000";
                description
                  "Configure the delay for clearing an alarm.";
              }
              leaf active-time {
                type uint16 {
                  range "0..600";
                }
                units "s";
                default "0";
                description
                  "Configure the time to activate an RMEP.";
              }
              leaf interface-tlv {
                type boolean;
                default "false";
                description
                  "Enable/disable interface status TLV in CCM.";
              }
              leaf sender-id-tlv {
                type boolean;
                default "false";
                description
                  "Enable/disable sender ID TLV in CCM.";
              }
              leaf port-status-tlv {
                type boolean;
                default "false";
                description
                  "Enable/disable port status TLV in CCM.";
              }
              leaf mip-create-type {
                type ma-mip-create-type;
                default "defer";
                description
                  "Configures the MIP create type of maintenance association.";
              }
              leaf unexpected-mep-alarm {
                type boolean;
                default "false";
                description
                  "Enable/disable unexpectedMep alarm.";
              }
              container ais {
                presence "Enable/disable AIS.";
                description
                  "Configure the function of all AIS instances.";
                leaf interval {
                  type ais-interval;
                  default "1s";
                  description
                    "Configure the interval at which AIS packets are sent.";
                }
                leaf level {
                  type uint8 {
                    range "0..7";
                  }
                  must "../level>../../../../level";
                  description
                    "Configure the level of AIS packets.";
                }
                leaf suppress-alarm-enable {
                  type boolean;
                  default "false";
                  description
                    "Enable/disable suppressing alarms.";
                }
              }
              container meps {
                description
                  "List of all MEPs.";
                list mep {
                  must "(pe-vlan and ce-vlan) or (not(pe-vlan) and not(ce-vlan))";
                  must "(direction and (if-name or peer-ip)) or (not(direction) and not(if-name) and not(peer-ip))";  
                  key "id";
                  description
                    "Configure a MEP point.";
                  leaf id {
                    type uint16 {
                      range "1..8191";
                    }
                    description
                      "Configure a MEP ID.";
                  }
                  choice type {
                    mandatory true;
                    description
                      "MEP type.";
                    case if-mep {
                      leaf if-name {
                        ext:operation-exclude update;
                        type leafref {
                          path "/ifm:ifm/ifm:interfaces/ifm:interface/ifm:name";
                        }
                        must "not(../../../meps/mep[if-name!=current()])";
                        mandatory true;
                        description
                          "Configure a MEP interface.";
                      }
                      choice tags {
                        description
                          "Configure the tags of a MEP.";
                        case two-tags {
                          leaf pe-vlan {
                            ext:operation-exclude update|delete;
                            type uint16 {
                              range "1..4094";
                            }
                            description
                              "Configure the PE VLAN of a MEP.";
                          }
                          leaf ce-vlan {
                            ext:operation-exclude update|delete;
                            type uint16 {
                              range "1..4094";
                            }
                            description
                              "Configure the CE VLAN of a MEP.";
                          }
                          description
                            "Configure the two tags of a MEP.";
                        }
                        case one-tag {
                          description
                            "Configure the dot1q VLAN of a MEP.";
                          leaf dot1q-vlan {
                            ext:operation-exclude update|delete;
                            type uint16 {
                              range "1..4094";
                            }
                            description
                              "Configure the dot1q VLAN of a MEP.";
                          }
                        }
                      }
                      leaf clear-arp {
                        when "../../../vlan-id";
                        type boolean;
                        must "../direction='outward'";
                        default "false";
                        description
                          "Enable/disable clear ARP.";
                      }
                      container lck {
                        presence "Enable/disable LCK.";
                        description
                          "Configure the LCK.";
                        leaf level {
                          type uint8 {
                            range "0..7";
                          }
                          must "../level > ../../../../../../level";
                          mandatory true;
                          description
                            "Configure the LCK message level.";
                        }
                      }
                      container eth-bn-receive {
                        when "(../../../vlan-id or ../../../no-bind) and (not (../pe-vlan)) and ../direction='outward'";
                        presence "Enable the ETN-BN receive function.";
                        description
                          "Configure ETH-BN receive.";
                      }
                      container port-link {
                        when "../direction='inward'";
                        must "(loc='true' or tlv='true')";
                        presence "Enable/disable port link in a MEP.";
                        description
                          "Configure port link.";
                        leaf port-link-holdoff {
                          type uint8 {
                            range "0..100";
                          }
                          units "100 ms";
                          default "0";
                          description
                            "Port linkage hold off time.";
                        }
                        leaf wtr {
                          type uint16 {
                            range "0..600";
                          }
                          units "s";
                          default "60";
                          description
                            "Port linkage wait to restore (WTR) time.";
                        }
                        leaf loc {
                          type boolean;
                          default "true";
                          description
                            "Enable/disable LOC.";
                        }
                        leaf tlv {
                          type boolean;
                          default "false";
                          description
                            "Enable/disable interface status TLV.";
                        }
                      }
                      description
                        "Configure a MEP on an interface.";
                    }
                    case pw-mep {
                      when "../../vsi-name";
                      leaf peer-ip {
                        ext:operation-exclude update;
                        type inet:ipv4-address-no-zone;
                        mandatory true;
                        description
                          "Configure the IP of peer end.";
                      }
                      leaf vc-id {
                        ext:operation-exclude update|delete;
                        when "../peer-ip";
                        type uint32 {
                          range "1..4294967295";
                        }
                        description
                         "Configure the ID of VC.";
                      }
                      leaf config-mac {
                        ext:operation-exclude update|delete;
                        type pub-type:mac-address;
                        description
                          "MAC address of a MEP."; 
                      }
                      description
                        "Configure a MEP on a PW.";
                    }
                  }
                  leaf direction {
                    ext:operation-exclude update|delete;
                    type direction;
                    must "(../direction='outward' and count(../../mep)=1) or not(../../../meps/mep[direction!=current()])";
                    description
                      "Configure the direction of a MEP.";
                  }
                  leaf cc-send-enable {
                    type boolean;
                    must "../cc-send-enable='false' or (../if-name)";
                    default "false";
                    description
                      "Enable/disable CCMs which can be sent.";
                  }
                  leaf rdi-alarm-disabled {
                    type boolean;
                    must "../rdi-alarm-disabled='false' or (../if-name or ../peer-ip)";
                    default "false";
                    description
                      "Enable/disable suppressing RDI alarm.";
                  }
                  leaf ais-alarm-disabled {
                    type boolean;
                    must "../ais-alarm-disabled='false' or (../if-name or ../peer-ip)";
                    default "false";
                    description
                      "Enable/disable suppressing AIS alarm.";
                  }
                }
              }
              container rmeps {
                description
                  "List of all remote maintenance points.";
                list rmep {
                  key "id";
                  description
                    "Configure a remote maintenance point.";
                  leaf id {
                    type uint16 {
                      range "1..8191";
                    }
                    description
                      "Configure the ID of a RMEP.";
                  }
                  leaf cc-recv-enabled {
                    type boolean;
                    default "false";
                    description
                      "Enable/disable CC receive.";
                  }
                }
              }
            }
          }
        }
      }
      container test-instances {
        description
          "List of all test instances.";
        list test-instance {
          key "test-id";
          description
            "Configure a test instance.";
          leaf test-id {
            type uint32 {
              range "1..4294967295";
            }
            description
              "Configure the ID of a test instance (65536 to 4294967295 is reserved for automatic allocation).";
          }
          leaf description {
            ext:operation-exclude update|delete;
            type string {
              length "1..63";
              pattern '[^\?]*';
            }
            description
              "Configure the description of a test instance.";
             
          }
          leaf md-name {
            ext:operation-exclude update;
            type leafref {
              path "/y1731/global-enable/mds/md/name";
            }
            //must "(../ma-name=/y1731:y1731/y1731:global-enable/y1731:mds/y1731:md[y1731:name=current()]/y1731:mas/y1731:ma/y1731:name)";
            mandatory true;
            description
              "Configure the name of a maintenance domain (MD).";
          }
          leaf ma-name {
            ext:operation-exclude update;
            type leafref {
              path "/y1731/global-enable/mds/md/mas/ma/name";
            }
            must "(/y1731:y1731/y1731:global-enable/y1731:mds/y1731:md[y1731:name=current()/../md-name]/y1731:mas/y1731:ma[y1731:name=current()])";
            mandatory true;
            description
              "Configure the name of a maintenance association (MA).";
          }
          leaf mep-id {
            ext:operation-exclude update;
            type leafref {
              path "/y1731/global-enable/mds/md/mas/ma/meps/mep/id";
            }
            //must "/y1731:y1731/y1731:global-enable/y1731:mds/y1731:md/y1731:mas/y1731:ma[y1731:name=current()]/y1731:meps/y1731:mep[y1731:id=current()]";
            must "/y1731:y1731/y1731:global-enable/y1731:mds/y1731:md[y1731:name=current()/../md-name]/y1731:mas/y1731:ma[y1731:name=current()/../ma-name]/y1731:meps/y1731:mep[y1731:id=current()]";
            mandatory true;
            description
              "Configure a MEP ID.";
          }
          choice remote {
            description
              "Configure the RMEP ID or MAC.";
            case rmep-id {
              leaf rmep-id {
                ext:operation-exclude update|delete;
                type leafref {
                  path "/y1731/global-enable/mds/md/mas/ma/rmeps/rmep/id";
                }
                must "/y1731:y1731/y1731:global-enable/y1731:mds/y1731:md[y1731:name=current()/../md-name]/y1731:mas/y1731:ma[y1731:name=current()/../ma-name]/y1731:rmeps/y1731:rmep[y1731:id=current()]";
                description
                  "Configure a RMEP ID.";
              }
              description
                "Configure a RMEP ID.";
            }
          }
          leaf priority {
            ext:operation-exclude update|delete;
            type uint8 {
              range "0..7";
            }
            must "(../priority and not(../peer-ip) and not(../vc-id)) or not(../priority)";
            description
              "Configure the priority of packets.";
          }
          leaf peer-ip {
            ext:operation-exclude update|delete;
            type inet:ipv4-address-no-zone;
            must "(../peer-ip and not(../priority)) or not(../peer-ip)";
            description
              "Configure the IP of peer end.";
          }
          leaf vc-id {
            ext:operation-exclude update|delete;
            type uint32 {
              range "1..4294967295";
            }
            must "((../vc-id and ../peer-ip and not(../priority)) or not(../vc-id))";
            description
              "Configure the ID of VC.";
          }
          leaf test-file-enable {
            ext:operation-exclude update|delete;
            type boolean;
            default "false";
            description
              "Enable/disable test ID file.";
          }
          container one-way-delay-send {
            presence "Enable/disable one-way DM send.";
            description
              "Configure a one-way delay measurement send instance.";
            leaf interval {
              ext:operation-exclude update;
              type interval;
              mandatory true;
              description
                "Configure the interval of one-way delay measurement send.";
            }
          }
          container one-way-delay-recv {
            presence "Enable/disable one-way DM receive.";
            description
              "Configure a one-way delay measurement receive instance.";
            leaf is-continue {
              ext:operation-exclude update|delete;
              type boolean;
              default "false";
              description
                "Enable/disable one-way delay continue measurement receive.";
            }
          }
          container two-way-delay-send {
            presence "Enable/disable two-way DM send.";
            description
              "Configure a two-way delay measurement send instance.";
            leaf interval {
              ext:operation-exclude update;
              type interval;
              mandatory true;
              description
                "Configure the interval of two-way delay measurement send.";
            }         
            leaf period {
              ext:operation-exclude update|delete;
              type uint16 {
                range "1..65535";
              }
              units "s";
              default "900";
              description
                "The value of measurement duration.";
            }
          }
          container two-way-delay-recv {
            description
              "Configure a two-way delay measurement receive instance.";
            leaf receive-enabled {
              type boolean;
              default "false";
              description
                "Enable/disable two-way delay measurement receive instance.";       
            }
          }
          container single-loss-send {
            must "not(../dual-loss/enabled='true')";
            presence "Enable/disable single loss send.";
            description
              "Configure a single-ended loss measurement send instance.";
            leaf interval {
              ext:operation-exclude update;
              type interval;
              mandatory true;
              description
                "Configure the interval of single-ended loss measurement send.";
            }
            leaf period {
              ext:operation-exclude update|delete;
              type uint16 {
                range "1..65535";
              }
              units "s";
              default "900";
              description
                "The value of measurement duration.";
            }
          }
          container single-loss-recv {
            description
              "Configure a single-ended loss measurement receive instance.";
            leaf enabled {
              type boolean;
              must "(not(../../dual-loss/enabled='true') or ((../../dual-loss/enabled='true') and (../enabled='false')))";
              default "false";
              description
                "Enable/disable single-ended loss measurement receive instance.";  
            }
          }
          container dual-loss {
            must "/y1731:y1731/y1731:global-enable/y1731:mds/y1731:md[y1731:name=current()/../md-name]/y1731:mas/y1731:ma[y1731:name=current()/../ma-name]/y1731:ccm-interval='100ms' or /y1731:y1731/y1731:global-enable/y1731:mds/y1731:md[y1731:name=current()/../md-name]/y1731:mas/y1731:ma[y1731:name=current()/../ma-name]/y1731:ccm-interval='1s' or /y1731:y1731/y1731:global-enable/y1731:mds/y1731:md[y1731:name=current()/../md-name]/y1731:mas/y1731:ma[y1731:name=current()/../ma-name]/y1731:ccm-interval='10s'";
            description
              "Configure a dual-ended loss measurement instance.";
            leaf enabled {
              type boolean;
              must "(((../enabled='true') and (not(../../single-loss-send/interval) and ../../single-loss-recv/enabled='false')) or (../enabled='false'))";
              default "false";
              description
                "Enable/disable dual-ended loss measurement instance.";    
            }
          }
          container synthetic-loss-send {
            presence "Enable/disable single synthetic LM send enable.";
            description
              "Configure a single ended synthetic send instance.";
            leaf interval {
              ext:operation-exclude update;
              type sslm-interval;
              mandatory true;
              description
                "Configuration interval of single ended synthetic send.";
            }
            leaf send-count {
              ext:operation-exclude update|delete;
              type uint16 {
                range "1..1000";
              }
              default "10";
              description
                "Configuration count of single ended synthetic send.";
            }
            leaf timeout {
              ext:operation-exclude update|delete;
              type uint8 {
                range "1..10";
              }
              default "5";
              description
                "Configuration time out value of single ended synthetic send.";
            }
            leaf period {
              ext:operation-exclude update|delete;
              type uint16 {
                range "1..65535";
              }
              default "900";
              description
                "Configuration period of single ended synthetic loss measurement.";
            }
          }
          container synthetic-loss-recv {
            presence "Enable/disable single synthetic LM receive.";
            description
              "Configure a single ended synthetic receive instance.";
            leaf timeout {
              ext:operation-exclude update|delete;
              type uint16 {
                range "10..300";
              }
              units "s";
              default "300";
              description
                "Configuration time out value of single ended synthetic receive.";
            }
          }
        }
      }
    }
  }
}
