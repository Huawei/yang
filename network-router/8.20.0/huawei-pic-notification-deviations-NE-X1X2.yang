/*
Copyright (C) 2019 Huawei Technologies Co., Ltd. All rights reserved.
*/
module huawei-pic-notification-deviations-NE-X1X2 {
  namespace "urn:huawei:yang:huawei-pic-notification-deviations-NE-X1X2";
  prefix pic-notification-devs-NE-X1X2;

  import huawei-pic-notification {
    prefix pic-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic-notification module.";

  revision 2019-11-06 {
    description
      "Initial revision.";
    reference
      "Huawei private.";
  }

  deviation "/pic-notification:flow-control-pause-frame-abnormal" {
    deviate not-supported;
  }
  deviation "/pic-notification:flow-control-pause-frame-abnormal-resume" {
    deviate not-supported;
  }
  deviation "/pic-notification:resource-dead-line" {
    deviate not-supported;
  }
  deviation "/pic-notification:resource-dead-line-resume" {
    deviate not-supported;
  }
  deviation "/pic-notification:upstream-pcm" {
    deviate not-supported;
  }
  deviation "/pic-notification:upstream-pcm-resume" {
    deviate not-supported;
  }
  deviation "/pic-notification:humidity-abnormal" {
    deviate not-supported;
  }
  deviation "/pic-notification:humidity-abnormal-resume" {
    deviate not-supported;
  }
  deviation "/pic-notification:input-error-exceed" {
    deviate not-supported;
  }
  deviation "/pic-notification:input-error-exceed-resume" {
    deviate not-supported;
  }
  deviation "/pic-notification:laser-shut" {
    deviate not-supported;
  }
  deviation "/pic-notification:laser-shut-resume" {
    deviate not-supported;
  }
  deviation "/pic-notification:negotiation-failed" {
    deviate not-supported;
  }
  deviation "/pic-notification:negotiation-failed-resume" {
    deviate not-supported;
  }
  deviation "/pic-notification:crc-error-warning" {
    deviate not-supported;
  }
  deviation "/pic-notification:crc-error-warning-resume" {
    deviate not-supported;
  }
  deviation "/pic-notification:trans-mode-inconsistent" {
    deviate not-supported;
  }
  deviation "/pic-notification:trans-mode-inconsistent-resume" {
    deviate not-supported;
  }
  deviation "/pic-notification:port-mode-change" {
    deviate not-supported;
  }
  deviation "/pic-notification:port-type-change" {
    deviate not-supported;
  }
  deviation "/pic-notification:remote-defect" {
    deviate not-supported;
  }
  deviation "/pic-notification:remote-defect-resume" {
    deviate not-supported;
  }
  deviation "/pic-notification:tim-trace-mismatch-resume" {
    deviate not-supported;
  }
  deviation "/pic-notification:license-resource-lack" {
    deviate not-supported;
  }
  deviation "/pic-notification:license-resource-lack-resume" {
    deviate not-supported;
  }
  deviation "/pic-notification:optical-unauthorized" {
    deviate not-supported;
  }
  deviation "/pic-notification:optical-unauthorized-resume" {
    deviate not-supported;
  }
}
