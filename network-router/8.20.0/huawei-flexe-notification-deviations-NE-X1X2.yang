/*
Copyright (C) 2019 Huawei Technologies Co., Ltd. All rights reserved.
*/
module huawei-flexe-notification-deviations-NE-X1X2 {
  namespace "urn:huawei:yang:huawei-flexe-notification-deviations-NE-X1X2";
  prefix flexe-notification-devs-NE-X1X2;

  import huawei-flexe-notification {
    prefix flexe-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-flexe-notification module.";

  revision 2019-11-06 {
    description
      "Initial revision.";
    reference
      "Huawei private.";
  }

  deviation "/flexe-notification:flexe-calendar-mismatch" {
    deviate not-supported;
  }
  deviation "/flexe-notification:flexe-calendar-mismatch-resume" {
    deviate not-supported;
  }
  deviation "/flexe-notification:flexe-band-mismatch" {
    deviate not-supported;
  }
  deviation "/flexe-notification:flexe-band-mismatch-resume" {
    deviate not-supported;
  }
  deviation "/flexe-notification:flexe-band-insufficient" {
    deviate not-supported;
  }
  deviation "/flexe-notification:flexe-band-insufficient-resume" {
    deviate not-supported;
  }
  deviation "/flexe-notification:flexe-client-mismatch" {
    deviate not-supported;
  }
  deviation "/flexe-notification:flexe-client-mismatch-resume" {
    deviate not-supported;
  }
  deviation "/flexe-notification:flexe-physical-delay" {
    deviate not-supported;
  }
  deviation "/flexe-notification:flexe-physical-delay-resume" {
    deviate not-supported;
  }
  deviation "/flexe-notification:flexe-physical-fcs-sd" {
    deviate not-supported;
  }
  deviation "/flexe-notification:flexe-physical-fcs-sd-resume" {
    deviate not-supported;
  }
  deviation "/flexe-notification:flexe-group-mismatch" {
    deviate not-supported;
  }
  deviation "/flexe-notification:flexe-group-mismatch-resume" {
    deviate not-supported;
  }
  deviation "/flexe-notification:flexe-local-fault" {
    deviate not-supported;
  }
  deviation "/flexe-notification:flexe-local-fault-resume" {
    deviate not-supported;
  }
  deviation "/flexe-notification:flexe-number-mismatch" {
    deviate not-supported;
  }
  deviation "/flexe-notification:flexe-number-mismatch-resume" {
    deviate not-supported;
  }
  deviation "/flexe-notification:flexe-remote-fault" {
    deviate not-supported;
  }
  deviation "/flexe-notification:flexe-remote-fault-resume" {
    deviate not-supported;
  }
  deviation "/flexe-notification:flexe-sub-ts-mismatch" {
    deviate not-supported;
  }
  deviation "/flexe-notification:flexe-sub-ts-mismatch-resume" {
    deviate not-supported;
  }
  deviation "/flexe-notification:flexe-negotiation-fail" {
    deviate not-supported;
  }
  deviation "/flexe-notification:flexe-negotiation-fail-resume" {
    deviate not-supported;
  }
  deviation "/flexe-notification:flexe-speed-mismatch" {
    deviate not-supported;
  }
  deviation "/flexe-notification:flexe-speed-mismatch-resume" {
    deviate not-supported;
  }

}
