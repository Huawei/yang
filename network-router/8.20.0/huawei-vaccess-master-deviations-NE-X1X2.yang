/*
Copyright (C) 2020 Huawei Technologies Co., Ltd. All rights reserved.
*/
module huawei-vaccess-master-deviations-NE-X1X2 {
  namespace "urn:huawei:yang:huawei-vaccess-master-deviations-NE-X1X2";
  prefix vaccess-master-devs-NE-X1X2;

  import huawei-vaccess-master {
    prefix vaccess-master;
  }
  import huawei-vaccess {
    prefix vaccess;
  }

  organization
    "Huawei Technologies Co., Ltd.";
  contact
    "Huawei Industrial Base
     Bantian, Longgang
     Shenzhen 518129
     People's Republic of China
     Website: http://www.huawei.com
     Email: support@huawei.com";
  description
    "Global Configuration.";

  revision 2020-03-23 {
    description
      "Init revision.";
    reference "Huawei private.";
  }
  deviation "/vaccess:vaccess/vaccess-master:master" {
    deviate not-supported;
  }
}
