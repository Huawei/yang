/*
Copyright (C) 2020 Huawei Technologies Co., Ltd. All rights reserved.
*/
module huawei-nvo3-statistics-deviations-NE-X1X2 {
  yang-version 1;
  namespace "urn:huawei:yang:huawei-nvo3-statistics-deviations-NE-X1X2";
  prefix nvo3-statistics-devs-NE-X1X2;

  import huawei-nvo3 {
    prefix nvo3;
  }
  import huawei-ifm {
    prefix ifm;
  }
  import huawei-nvo3-statistics {
    prefix nvo3-statistics;
  }
  import huawei-bd {
    prefix bd;
  }

  organization
    "Huawei Technologies Co., Ltd.";
  contact
    "Huawei Industrial Base
     Bantian, Longgang
     Shenzhen 518129
     People's Republic of China
     Website: http://www.huawei.com
     Email: support@huawei.com";
  description
    "Management of NVO3.";

  revision 2020-06-16 {
    description
      "Init revision.";
    reference "Huawei private.";
  }

  typedef vxlan-mode-deviations {
    type enumeration {
      enum l2 {
        value 0;
        description
          "Layer 2.";
      }
      enum l3 {
        value 1;
        description
          "Layer 3.";
      }
    }
    description
      "VXLAN mode.";
  }

  deviation "/ifm:ifm/ifm:interfaces/ifm:interface/nvo3-statistics:nvo3-vtep-statistics/nvo3-statistics:nvo3-vtep-statistic/nvo3-statistics:vni" {
    deviate add {
      must "(/nvo3:nvo3/nvo3:vni-labels/nvo3:vni-label[nvo3:vni=current()]/nvo3-statistics:statistics/nvo3-statistics:enable = 'false') or not(../vni)";
    }
  }
  deviation "/ifm:ifm/ifm:interfaces/ifm:interface/nvo3-statistics:nvo3-vtep-statistics/nvo3-statistics:nvo3-vtep-statistic/nvo3-statistics:vni" {
    deviate add {
      must "not (/bd:bd/bd:instances/bd:instance/nvo3:nvo3/nvo3:vni-list[nvo3:vni = current()]/nvo3:split-horizon = 'true')";
    }
  }
  deviation "/ifm:ifm/ifm:interfaces/ifm:interface/nvo3-statistics:nvo3-vtep-statistics/nvo3-statistics:nvo3-vtep-statistic/nvo3-statistics:mode" {
    deviate replace {
      type nvo3-statistics-devs-NE-X1X2:vxlan-mode-deviations;
    }
  }
}
