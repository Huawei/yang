/*
Copyright (C) 2019 Huawei Technologies Co., Ltd. All rights reserved.
*/
module huawei-multicast-forward-deviations-NE5000E {
  namespace "urn:huawei:yang:huawei-multicast-forward-deviations-NE5000E";
  prefix multicast-forward-devs-NE5000E;

  import huawei-multicast-forward {
    prefix multicast-forward;
  }

  import huawei-ifm {
    prefix ifm;
  }

  import huawei-qos {
    prefix qos;
  }

  organization
    "Huawei Technologies Co., Ltd.";

  contact
    "Huawei Industrial Base
     Bantian, Longgang
     Shenzhen 518129
     People's Republic of China
     Website: http://www.huawei.com
     Email: support@huawei.com";

  description
    "This module defines deviation statements for huawei-multicast-forward module.";

  revision 2019-11-06 {
    description
      "Initial revision.";
    reference
      "Huawei private.";
  }

  typedef frr-type-deviations {
    type enumeration {
      enum "init" {
        value 0;
        description 
          "Init type.";
      }
      enum "normal" {
        value 1;
        description 
          "Normal FRR type.";
      }
      enum "ngmvpn" {
        value 2;
        description 
          "NGMVPN type.";
      }
    }
    description 
      "Fast re-router type.";
  }

  deviation "/multicast-forward:multicast-forward/multicast-forward:global/multicast-forward:shaping-enable" {
    deviate not-supported;
  }
  deviation "/multicast-forward:multicast-forward/multicast-forward:global/multicast-forward:bw-car-enable" {
    deviate not-supported;
  }
  deviation "/multicast-forward:multicast-forward/multicast-forward:global/multicast-forward:fragment-enable" {
    deviate not-supported;
  }
  deviation "/multicast-forward:multicast-forward/multicast-forward:nat" {
    deviate not-supported;
  }
  deviation "/multicast-forward:multicast-forward/multicast-forward:egress-forward-mode" {
    deviate not-supported;
  }
  deviation "/multicast-forward:multicast-forward/multicast-forward:mcfwd-entrys/multicast-forward:mcfwd-entry/multicast-forward:forward-infors/multicast-forward:forward-infor/multicast-forward:bas-flag" {
    deviate not-supported;
  }
  deviation "/multicast-forward:multicast-forward/multicast-forward:multicast-speed-states" {
    deviate not-supported;
  }
  deviation "/multicast-forward:multicast-forward/multicast-forward:spatial-multicast" {
    deviate not-supported;
  }
  deviation "/multicast-forward:multicast-forward/multicast-forward:multicast-remote-users" {
    deviate not-supported;
  }
  deviation "/multicast-forward:multicast-forward/multicast-forward:multicast-outgoing-interface-statics/multicast-forward:multicast-outgoing-interface-static/multicast-forward:ipv4-used-number" {
    deviate not-supported;
  }
  deviation "/multicast-forward:multicast-forward/multicast-forward:multicast-outgoing-interface-statics/multicast-forward:multicast-outgoing-interface-static/multicast-forward:ipv6-used-number" {
    deviate not-supported;
  }
  deviation "/multicast-forward:multicast-forward/multicast-forward:multicast-outgoing-interface-statics/multicast-forward:multicast-outgoing-interface-static/multicast-forward:others-number" {
    deviate not-supported;
  }
  deviation "/multicast-forward:multicast-forward/multicast-forward:l3-egress-statistics" {
    deviate not-supported;
  }
  deviation "/multicast-forward:multicast-forward/multicast-forward:l2-egress-statistics" {
    deviate not-supported;
  }
  deviation "/multicast-forward:multicast-forward/multicast-forward:static-frr/multicast-forward:static-frr-statuss/multicast-forward:static-frr-status/multicast-forward:primary-source-address" {
    deviate not-supported;
  }
  deviation "/multicast-forward:multicast-forward/multicast-forward:static-frr/multicast-forward:static-frr-statuss/multicast-forward:static-frr-status/multicast-forward:backup-source-address" {
    deviate not-supported;
  }
  deviation "/multicast-forward:reset-bas-multicast-rui-statics" {
    deviate not-supported;
  }
  deviation "/multicast-forward:send-igmp-packet" {
    deviate not-supported;
  }
  deviation "/multicast-forward:reset-l3-egress-all-statistics" {
    deviate not-supported;
  }
  deviation "/multicast-forward:reset-l3-egress-statistics" {
    deviate not-supported;
  }
  deviation "/multicast-forward:reset-l2-egress-all-statistics" {
    deviate not-supported;
  }
  deviation "/multicast-forward:reset-vlan-egress-statistics" {
    deviate not-supported;
  }
  deviation "/multicast-forward:reset-vsi-egress-statistics" {
    deviate not-supported;
  }
  deviation "/multicast-forward:reset-bd-egress-statistics" {
    deviate not-supported;
  }
  deviation "/multicast-forward:single-fast-switch" {
    deviate not-supported;
  }
  deviation "/multicast-forward:group-fast-switch" {
    deviate not-supported;
  }
  deviation "/multicast-forward:get-multicast-forwarding-device" {
    deviate not-supported;
  }
  deviation "/ifm:ifm/ifm:interfaces/ifm:interface/multicast-forward:multicast-forward/multicast-forward:shaping" {
    deviate not-supported;
  }
  deviation "/qos:qos/qos:classifier-template/qos:traffic-behaviors/qos:traffic-behavior/multicast-forward:behavior-bind-multicast-nat-instance" {
    deviate not-supported;
  }
  deviation "/multicast-forward:multicast-forward/multicast-forward:static-frr/multicast-forward:static-frr-statuss/multicast-forward:static-frr-status/multicast-forward:frr-type" {
    deviate replace {
      type multicast-forward-devs-NE5000E:frr-type-deviations;
    }
  }

}
