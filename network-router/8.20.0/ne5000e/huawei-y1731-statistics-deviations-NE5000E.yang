/*
Copyright (C) 2019 Huawei Technologies Co., Ltd. All rights reserved.
*/
module huawei-y1731-statistics-deviations-NE5000E {
  namespace "urn:huawei:yang:huawei-y1731-statistics-deviations-NE5000E";
  prefix "y1731-statistics-devs-NE5000E";
  
  import huawei-y1731 {
    prefix y1731;
  }
  import huawei-devm {
    prefix "devm";
  }
  import huawei-y1731-statistics {
    prefix "y1731-statistics";
  }

  organization
    "Huawei Technologies Co., Ltd.";
  contact
    "Huawei Industrial Base
     Bantian, Longgang
     Shenzhen 518129
     People's Republic of China
     Website: http://www.huawei.com
     Email: support@huawei.com";
  description
    "Carrier Grade NAT.";
  revision 2019-10-28 {
    description
      "The modifications in the schema file are synchronized to the YANG file.";
    reference
      "Huawei private.";
  }
  
  deviation /devm:devm/devm:mpu-boards/devm:mpu-board/y1731-statistics:cfm-mac-level-enable-mpu {
    deviate not-supported;
  }

  deviation /y1731:y1731/y1731-statistics:inner-priority {
    deviate not-supported;
  }
  deviation /y1731:y1731/y1731-statistics:cfm-level-check {
    deviate not-supported;
  }
}
