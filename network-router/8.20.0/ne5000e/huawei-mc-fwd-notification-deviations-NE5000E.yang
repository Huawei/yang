/*
Copyright (C) 2019 Huawei Technologies Co., Ltd. All rights reserved.
*/
module huawei-mc-fwd-notification-deviations-NE5000E {
  namespace "urn:huawei:yang:huawei-mc-fwd-notification-deviations-NE5000E";
  prefix multicast-forward-notification-devs-NE5000E;

  import huawei-mc-fwd-notification {
    prefix multicast-forward-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-mc-fwd-notification module.";

  revision 2019-11-06 {
    description
      "Initial revision.";
    reference
      "Huawei private.";
  }

  deviation "/multicast-forward-notification:nat-igmp-report-event" {
    deviate not-supported;
  }

}
