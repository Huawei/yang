/*
Copyright (C) 2019 Huawei Technologies Co., Ltd. All rights reserved.
*/
module huawei-clocksync-cluster-deviations-NE5000E {
  namespace "urn:huawei:yang:huawei-clocksync-cluster-deviations-NE5000E";
  prefix "clocksync-cluster-devs-NE5000E";

  import huawei-clocksync-cluster {
    prefix "clocksync-cluster";
  }
  
  import huawei-ifm {
    prefix "ifm";
  }
  organization
    "Huawei Technologies Co., Ltd.";
  contact
    "Huawei Industrial Base
     Bantian, Longgang
     Shenzhen 518129
     People's Republic of China
     Website: http://www.huawei.com
     Email: support@huawei.com";
  description
    "System clock synchronization management, including frequency synchronization and time synchronization.";
  revision 2019-11-01 {
    description
      "Init revision.";
    reference
      "Huawei private.";
  }

deviation /ifm:ifm/ifm:interfaces/ifm:interface/clocksync-cluster:vinter-links{
  deviate not-supported;
}

}
