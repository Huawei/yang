/*
Copyright (C) 2019 Huawei Technologies Co., Ltd. All rights reserved.
*/
module huawei-macsec-deviations-NE5000E {
  namespace "urn:huawei:yang:huawei-macsec-deviations-NE5000E";
  prefix "macsec-devs-NE5000E";

  import huawei-macsec {
    prefix "macsec";
  }
  import huawei-license {
    prefix lcs;
  }

  organization
    "Huawei Technologies Co., Ltd.";
  contact
    "Huawei Industrial Base
     Bantian, Longgang
     Shenzhen 518129
     People's Republic of China
     Website: http://www.huawei.com
     Email: support@huawei.com";
  description
    "Media Access Control (MAC) Security.";
  revision 2019-06-27 {
    description
      "Init revision.";
    reference
      "Huawei private.";
  }

  deviation /lcs:license/lcs:license-items/lcs:license-item/macsec:port-macsecs {
    deviate not-supported;
  }
}
