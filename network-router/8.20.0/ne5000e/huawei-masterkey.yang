/*
Copyright (C) 2019-2020 Huawei Technologies Co., Ltd. All rights reserved.
*/
module huawei-masterkey {
  namespace "urn:huawei:yang:huawei-masterkey";
  prefix masterkey;
  import ietf-yang-types {
    prefix yang;
  }
  import huawei-pub-type {
    prefix pub-type;
  }
  import huawei-extension {
    prefix ext;
  }
  
  organization
    "Huawei Technologies Co., Ltd.";
  contact
    "Huawei Industrial Base
     Bantian, Longgang
     Shenzhen 518129
     People's Republic of China
     Website: http://www.huawei.com
     Email: support@huawei.com";
  description
    "Master key.";
  revision 2020-03-20 {
    description
      "Fixed units and description problems.";
    reference
      "Huawei private.";
  }
  revision 2019-05-22 {
    description
      "Initial revision.";
    reference
      "Huawei private.";
  }
  ext:task-name "system";
  typedef mk-config-type {
    type enumeration {
      enum "default" {
        value 1;
        description
          "Default master key.";
      }
      enum "user-defined" {
        value 2;
        description
          "User defined master key.";
      }
      enum "auto-update" {
        value 3;
        description
          "Auto update master key.";
      }
    }
    description
      "The config type of master key.";
  }
  typedef mk-modify-result {
    type enumeration {
      enum "success" {
        value 1;
        description
          "Success.";
      }
      enum "operating" {
        value 2;
        description
          "Operating.";
      }
      enum "failure" {
        value 3;
        description
          "Failure.";
      }
    }
    description
      "The status of operation.";
  }
  container masterkey {
    description
      "Master key.";
    container current-type {
      config false;
      description
        "Operational state of master key current type.";
      leaf type {
        type mk-config-type;
        description
          "Master key current type.";
      }
    }
    container modify-result {
      config false;
      description
        "Operational state of master key modify information.";
      leaf modify-start-time {
        type yang:date-and-time;
        description
          "Start time.";
      }
      leaf modify-end-time {
        type yang:date-and-time;
        description
          "End time.";
      }
      leaf modify-result {
        type mk-modify-result;
        description
          "Modify result.";
      }
      leaf modify-error-reason {
        type string {
          length "1..128";
        }
        description
          "Modify error reason.";
      }
    }
  container auto-update {
      description
        "Configure master key auto update.";
      leaf interval {
         type uint32 {
          range "1..3650";
        }
        units "d";
        description
          "Auto update interval.";
      }
    }
  }
  rpc set-masterkey {
    description
      "Modify master key.";
    ext:node-ref "/masterkey";
    input {
      leaf new-masterkey {
        type pub-type:password-extend{
            length "20..32";
        }
        mandatory true;
        description
          "New master key.";
      }
    }
  }
  rpc clear-masterkey {
    description
      "Delete historical master key.";
    ext:node-ref "/masterkey";
  }
}
