/*
Copyright (C) 2020 Huawei Technologies Co., Ltd. All rights reserved.
*/
module huawei-vrrp-deviations-NE5000E {
  yang-version 1;
  namespace "urn:huawei:yang:huawei-vrrp-deviations-NE5000E";
  prefix vrrp-devs-NE5000E;

  import huawei-vrrp {
    prefix vrrp;
  }
  import huawei-ifm {
    prefix ifm;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "Global VRRP configuration.";

  revision 2020-03-19 {
    description
      "Initial revision.";
    reference "Huawei private.";
  }

  deviation "/vrrp:vrrp/vrrp:global/vrrp:gratuitous-timeout" {
    deviate replace {
      default "120";
    }
  }
  deviation "/vrrp:vrrp/vrrp:global/vrrp:smooth-switch-time" {
    deviate not-supported;
  }
  deviation "/vrrp:vrrp/vrrp:global/vrrp:unicast-port" {
    deviate not-supported;
  }
  deviation "/ni:network-instance/ni:instances/ni:instance/vrrp:vrrp/vrrp:groups/vrrp:group/vrrp:hold-multi" {
    deviate not-supported;
  }
  deviation "/ifm:ifm/ifm:interfaces/ifm:interface/vrrp:vrrp/vrrp:backup-groups/vrrp:arpsend-simple" {
    deviate not-supported;
  }
  deviation "/ifm:ifm/ifm:interfaces/ifm:interface/vrrp:vrrp/vrrp:backup-groups/vrrp:advertise-send-mode" {
    deviate not-supported;
  }
  deviation "/ifm:ifm/ifm:interfaces/ifm:interface/vrrp:vrrp/vrrp:track-admins" {
    deviate not-supported;
  }
}
