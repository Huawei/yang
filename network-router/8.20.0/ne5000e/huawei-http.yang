/*
Copyright (C) 2020 Huawei Technologies Co., Ltd. All rights reserved.
*/
module huawei-http {
  namespace "urn:huawei:yang:huawei-http";
  prefix http;
  import huawei-extension {
    prefix ext;
  }
  import huawei-ssl {
    prefix ssl;
  }
  import huawei-acl {
    prefix acl;
  }
  import huawei-pub-type {
    prefix pub-type;
  }
  organization
    "Huawei Technologies Co., Ltd.";
  contact
    "Huawei Industrial Base
     Bantian, Longgang
     Shenzhen 518129
     People's Republic of China
     Website: http://www.huawei.com
     Email: support@huawei.com";
  description
    "HTTP server and client.";
  revision 2020-07-21 {
    description
      "Initial revision.";
    reference
      "Huawei private.";
  }
  typedef http-server-type {
    type enumeration {
      enum "restconf" {
        value 1;
        description
          "Restconf: restconf service type.";
      }
    }
    description
      "HTTP service type.";
  }
  ext:task-name  "https";
  container http {
    description
      "HTTP.";
    container comp-enable {
      description
        "Configure HTTP enable.";
      leaf comp-enable {
        type boolean;
          default "false";
        description
          "Enable/disable HTTP function.";
      }
    }
    container client {
      when "../comp-enable/comp-enable = 'true'";
      description
        "Configure HTTP client.";
        leaf ssl-policy-name {
          type leafref {
            path "/ssl:ssl/ssl:ssl-policys/ssl:ssl-policy/ssl:policy-name";
          }
          description
            "SSL policy name.";
        }
        leaf ssl-verify-type {
          when "../ssl-policy-name";
          type boolean;
          default "false";
          description
            "Enable/disable SSL verify peer.";
        }
    }
    container servers {
      when "../comp-enable/comp-enable = 'true'";
      description
        "List of HTTP server configuration.";
      list server {
        key "server-type";
        description
          "Configure HTTP server.";
		leaf server-type {
		  type http-server-type;
		  description
			"HTTP server type.";
		}
		leaf server-enable {
		  type boolean;
		  must "../secure-enable != 'true' or (../secure-enable = 'true' and ../server-enable = 'false')" ;
		  default "false";
		  description
			"Enable/disable HTTP server.";
		}
		leaf secure-enable {
		  type boolean;
		  must "../server-enable != 'true' or (../server-enable = 'true' and ../secure-enable = 'false')" ;
		  default "false";
		  description
			"Enable/disable HTTP secure server.";
		}
		leaf server-port {
		  type uint32 {
			range "80 | 1025..65535";
		  }
		  default "80";
		  description
			"HTTP server port.";
		}
		leaf secure-port {
		  type uint32 {
			range "443 | 1025..65535";
		  }
		  default "443";
		  description
			"HTTP secure server port.";
		}
		leaf acl-name {
			type leafref {
			  path "/acl:acl/acl:groups/acl:group/acl:identity";
			}
			must "/acl:acl/acl:groups/acl:group[acl:identity=current()]/acl:type='basic' or /acl:acl/acl:groups/acl:group[acl:identity=current()]/acl:type='advance'";
		  description
			"HTTP server ACL name or number for IPv4 connections.";
		}
		leaf ssl-policy-name {
		  type leafref {
			path "/ssl:ssl/ssl:ssl-policys/ssl:ssl-policy/ssl:policy-name";
		  }
		  must "../secure-enable = 'true' ";
		  description
			"SSL policy name.";
		}
		leaf ssl-verify-type {
		  type boolean;
		  must "../secure-enable = 'true'  and ../ssl-policy-name";
		  default "false";
		  description
			"Enable/disable SSL verify.";
		}
		leaf idle-timeout {
		  type uint32 {
			range "1..60";
		  }
		  default "20";
		  description
			"Idle timeout.";
		}
	  }
    }
    container server-source {
      when "../comp-enable/comp-enable = 'true' and count(../servers/server[server-type = 'restconf']) > 0 ";
      description
        "Configure http server interfaces.";
      leaf src-interface {
        when "../all-interface = 'false'";
        type pub-type:if-name;
        description
          "Specify the source interface name. The specified source interface must exist and an IP address must be configured on the interface.";
      }
      leaf all-interface {
        type boolean;
        default "false";
        description
          "Enable/disable specify all interfaces.";
      }
    }
  }
}
