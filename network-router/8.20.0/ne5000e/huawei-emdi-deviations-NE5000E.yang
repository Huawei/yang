/*
Copyright (C) 2019 Huawei Technologies Co., Ltd. All rights reserved.
*/
module huawei-emdi-deviations-NE5000E {
  namespace "urn:huawei:yang:huawei-emdi-deviations-NE5000E";
  prefix emdi-devs-NE5000E;

  import huawei-emdi {
    prefix emdi;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-emdi module.";

  revision 2019-11-06 {
    description
      "Initial revision.";
    reference
      "Huawei private.";
  }

  deviation "/emdi:emdi/emdi:emdi-enable/emdi:emdi-channel-groups/emdi:emdi-channel-group/emdi:emdi-channels/emdi:emdi-channel/emdi:channel-group-parameters/emdi:vlan-id" {
    deviate not-supported;
  }
  deviation "/emdi:emdi/emdi:emdi-enable/emdi:emdi-channel-groups/emdi:emdi-channel-group/emdi:emdi-channels/emdi:emdi-channel/emdi:channel-group-parameters/emdi:vsi-name" {
    deviate not-supported;
  }
  deviation "/emdi:emdi/emdi:emdi-enable/emdi:emdi-channel-groups/emdi:emdi-channel-group/emdi:emdi-channels/emdi:emdi-channel/emdi:channel-group-parameters/emdi:bd-id" {
    deviate not-supported;
  }
  deviation "/emdi:emdi/emdi:emdi-enable/emdi:emdi-lpu-groups/emdi:emdi-lpu-group/emdi:bind-lpu/emdi:bind-slots/emdi:slot" {
    deviate replace {
      type leafref {
        path "/devm:devm/devm:lpu-boards/devm:lpu-board/devm:position";
      }
    }
  }

}
