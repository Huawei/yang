/*
Copyright (C) 2019 Huawei Technologies Co., Ltd. All rights reserved.
*/
module huawei-mvpn-forward-deviations-NE5000E {
  namespace "urn:huawei:yang:huawei-mvpn-forward-deviations-NE5000E";
  prefix "mvpn-forward-devs-NE5000E";

  import huawei-mvpn-forward {
    prefix "mvpn-forward";
  }
  import huawei-network-instance {
    prefix "ni";
  }
  import huawei-l3vpn {
    prefix l3vpn;
  }
  import huawei-mvpn {
    prefix mvpn;
  }
  organization
    "Huawei Technologies Co., Ltd.";
  contact
    "Huawei Industrial Base
     Bantian, Longgang
     Shenzhen 518129
     People's Republic of China
     Website: http://www.huawei.com
     Email: support@huawei.com";
  description
    "Mvpn forwarding table.";
  revision 2019-06-01 {
    description
      "Init revision.";
    reference
      "Huawei private.";
  }

  deviation /mvpn-forward:mvpn-forward/mvpn-forward:global/mvpn-forward:multicast-vpn-slots { 
    deviate not-supported; 
  }
  deviation /mvpn-forward:mvpn-forward/mvpn-forward:global/mvpn-forward:ttl-propagate { 
    deviate not-supported; 
  }
  deviation /ni:network-instance/ni:instances/ni:instance/l3vpn:afs/l3vpn:af/mvpn:mvpn/mvpn:mvpn-type/mvpn:ng-mvpn/mvpn:ng/mvpn-forward:multicast-wtr { 
    deviate not-supported; 
  }
  deviation /mvpn-forward:mvpn-forward/mvpn-forward:global/mvpn-forward:ng-mvpn-forward-mode { 
    deviate not-supported; 
  }
}
