/*
Copyright (C) 2019 Huawei Technologies Co., Ltd. All rights reserved.
*/
module huawei-unicast-forward-deviations-NE5000E {
  namespace "urn:huawei:yang:huawei-unicast-forward-deviations-NE5000E";
  prefix unicast-forward-devs-NE5000E;

  import huawei-unicast-forward {
    prefix unicast-forward;
  }

  import huawei-ifm {
    prefix ifm;
  }

  import huawei-said-frame {
    prefix sf;
  }

  import huawei-devm-vnf {
    prefix devm-vnf;
  }

  import huawei-devm {
    prefix devm;
  }

  import huawei-license {
    prefix lcs;
  }

  organization
    "Huawei Technologies Co., Ltd.";

  contact
    "Huawei Industrial Base
     Bantian, Longgang
     Shenzhen 518129
     People's Republic of China
     Website: http://www.huawei.com
     Email: support@huawei.com";

  description
    "This module defines deviation statements for huawei-unicast-forward module.";

  revision 2019-11-06 {
    description
      "Initial revision.";
    reference
      "Huawei private.";
  }

  deviation "/unicast-forward:unicast-forward/unicast-forward:global-uc-attribute/unicast-forward:ipv4-force-frag" {
    deviate not-supported;
  }
  deviation "/unicast-forward:unicast-forward/unicast-forward:global-uc-attribute/unicast-forward:mtu-force-frag" {
    deviate not-supported;
  }
  deviation "/unicast-forward:unicast-forward/unicast-forward:global-uc-attribute/unicast-forward:trunk-nd-mode" {
    deviate not-supported;
  }
  deviation "/unicast-forward:unicast-forward/unicast-forward:global-uc-attribute/unicast-forward:trunk-arp-mode" {
    deviate not-supported;
  }
  deviation "/unicast-forward:unicast-forward/unicast-forward:high-re-modes" {
    deviate not-supported;
  }
  deviation "/unicast-forward:unicast-forward/unicast-forward:global-gre" {
    deviate not-supported;
  }
  deviation "/ifm:ifm/ifm:interfaces/ifm:interface/unicast-forward:unicast-forward/unicast-forward:poison-reverse" {
    deviate not-supported;
  }
  deviation "/ifm:ifm/ifm:interfaces/ifm:interface/unicast-forward:unicast-forward/unicast-forward:ip-priority-select" {
    deviate not-supported;
  }
  deviation "/ifm:ifm/ifm:interfaces/ifm:interface/unicast-forward:unicast-forward/unicast-forward:mac-change-notify-arp" {
    deviate not-supported;
  }
  deviation "/ifm:ifm/ifm:interfaces/ifm:interface/unicast-forward:unicast-forward/unicast-forward:mac-change-notify-nd-disable" {
    deviate not-supported;
  }
  deviation "/devm:devm/devm:lpu-boards/devm:lpu-board/unicast-forward:unicast-forward/unicast-forward:gre-ttl-mode" {
    deviate not-supported;
  }
  deviation "/devm:devm/devm:lpu-boards/devm:lpu-board/unicast-forward:unicast-forward/unicast-forward:l3-lcs-capacitys" {
    deviate not-supported;
  }
  deviation "/devm:devm/devm:mpu-boards/devm:mpu-board/unicast-forward:unicast-forward" {
    deviate not-supported;
  }
  deviation "/lcs:license/lcs:license-items/lcs:license-item/unicast-forward:port-l3vpn-evpns" {
    deviate not-supported;
  }
  deviation "/lcs:license/lcs:license-items/lcs:license-item/unicast-forward:port-service-enhances" {
    deviate not-supported;
  }
  deviation "/lcs:license/lcs:license-items/lcs:license-item/unicast-forward:port-aggregations" {
    deviate not-supported;
  }
  deviation "/lcs:license/lcs:license-items/lcs:license-item/unicast-forward:port-core-aggregations" {
    deviate not-supported;
  }
  deviation "/lcs:license/lcs:license-items/lcs:license-item/unicast-forward:port-peerings" {
    deviate not-supported;
  }
  deviation "/lcs:license/lcs:license-items/lcs:license-item/unicast-forward:port-srv6s" {
    deviate not-supported;
  }
  deviation "/lcs:license/lcs:resource-usages/lcs:resource-usage/unicast-forward:port-l3vpn-evpns" {
    deviate not-supported;
  }
  deviation "/lcs:license/lcs:resource-usages/lcs:resource-usage/unicast-forward:port-service-enhances" {
    deviate not-supported;
  }
  deviation "/lcs:license/lcs:resource-usages/lcs:resource-usage/unicast-forward:port-aggregations" {
    deviate not-supported;
  }
  deviation "/lcs:license/lcs:resource-usages/lcs:resource-usage/unicast-forward:port-core-aggregations" {
    deviate not-supported;
  }
  deviation "/lcs:license/lcs:resource-usages/lcs:resource-usage/unicast-forward:port-peerings" {
    deviate not-supported;
  }
  deviation "/lcs:license/lcs:resource-usages/lcs:resource-usage/unicast-forward:port-srv6s" {
    deviate not-supported;
  }
  deviation "/sf:said-frame/unicast-forward:ip-nices" {
    deviate not-supported;
  }
  deviation "/sf:said-frame/unicast-forward:global-uc-attribute" {
    deviate not-supported;
  }
  deviation "/devm-vnf:devm-vnf/devm-vnf:vnf-boards/devm-vnf:vnf-board/unicast-forward:unicast-forward" {
    deviate not-supported;
  }

}
