/*
Copyright (C) 2019 Huawei Technologies Co., Ltd. All rights reserved.
*/
module huawei-syslog-deviations-NE5000E {
  namespace "urn:huawei:yang:huawei-syslog-deviations-NE5000E";
  prefix syslog-devs-NE5000E;

  import huawei-syslog {
    prefix syslog;
  }

  organization
    "Huawei Technologies Co., Ltd.";
  contact
    "Huawei Industrial Base
     Bantian, Longgang
     Shenzhen 518129
     People's Republic of China
     Website: http://www.huawei.com
     Email: support@huawei.com";
  description
    "Deviation of syslog module.";

  revision 2019-04-23 {
    description
      "Init revision.";
    reference "Huawei private.";
  }

  typedef logfile-type-deviations {
    type enumeration {
      enum log {
        value 1;
        description
          "Log logfile.";
      }
      enum security {
        value 3;
        description
          "Security logfile.";
      }
      enum debug {
        value 6;
        description
          "Debug logfile.";
      }
    }
    description
      "The type of log.";
  }

  deviation "/syslog:syslog/syslog:domain-servers/syslog:domain-server/syslog:is-brief-format" {
    deviate not-supported;
  }
  deviation "/syslog:syslog/syslog:servers/syslog:server/syslog:host-name" {
    deviate not-supported;
  }
  deviation "/syslog:syslog/syslog:servers/syslog:server/syslog:is-activated" {
    deviate not-supported;
  }
  deviation "/syslog:syslog/syslog:servers/syslog:server/syslog:facility-mask" {
    deviate not-supported;
  }
  deviation "/syslog:syslog/syslog:servers/syslog:server/syslog:severity-mask" {
    deviate not-supported;
  }
  deviation "/syslog:syslog/syslog:servers/syslog:server/syslog:is-brief-format" {
    deviate not-supported;
  }
  deviation "/syslog:syslog/syslog:global-parameter/syslog:character-set" {
    deviate not-supported;
  }
  deviation "/syslog:syslog/syslog:logfiles/syslog:logfile/syslog:logfile-type" {
    deviate replace {
      type syslog-devs-NE5000E:logfile-type-deviations;
    }
  }
}
