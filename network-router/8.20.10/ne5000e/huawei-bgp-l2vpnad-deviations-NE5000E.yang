/*
Copyright (C) 2019 Huawei Technologies Co., Ltd. All rights reserved.
*/
module huawei-bgp-l2vpnad-deviations-NE5000E {
  namespace "urn:huawei:yang:huawei-bgp-l2vpnad-deviations-NE5000E";
  prefix bgp-l2vpnad-devs-NE5000E;

  import huawei-bgp {
    prefix bgp;
  }
  import huawei-network-instance {
    prefix ni;
  }
  import huawei-bgp-l2vpnad {
    prefix bgp-l2vpnad;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2019-09-09 {
    description
      "Initial revision.";
    reference "Huawei private.";
  }

  deviation "/ni:network-instance/ni:instances/ni:instance/bgp:bgp/bgp:base-process/bgp:afs/bgp:af/bgp-l2vpnad:l2vpnad/bgp-l2vpnad:common/bgp-l2vpnad:multi-homing-nonstand" {
    deviate not-supported;
  }
}
