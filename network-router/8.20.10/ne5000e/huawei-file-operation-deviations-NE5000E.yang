/*
Copyright (C) 2019 Huawei Technologies Co., Ltd. All rights reserved.
*/
module huawei-file-operation-deviations-NE5000E {
  namespace "urn:huawei:yang:huawei-file-operation-deviations-NE5000E";
  prefix file-operation-devs-NE5000E;

  import huawei-file-operation {
    prefix file-operation;
  }

  organization
    "Huawei Technologies Co., Ltd.";
  contact
    "Huawei Industrial Base
     Bantian, Longgang
     Shenzhen 518129
     People's Republic of China
     Website: http://www.huawei.com
     Email: support@huawei.com";
  description
    "This module defines deviation statements for huawei-file-operation module.";

  revision 2019-11-06 {
    description
      "Initial revision.";
    reference "Huawei private.";
  }

  deviation "/file-operation:file-operation/file-operation:disk-usages" {
    deviate not-supported;
  }
  deviation "/file-operation:reset-recycle-bin" {
    deviate not-supported;
  }
  deviation "/file-operation:copy-file/file-operation:input/file-operation:all" {
    deviate not-supported;
  }
  deviation "/file-operation:delete-file/file-operation:input/file-operation:all" {
    deviate not-supported;
  }
}
