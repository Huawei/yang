/*
Copyright (C) 2019 Huawei Technologies Co., Ltd. All rights reserved.
*/
module huawei-ospfv3-deviations-NE5000E {
  namespace "urn:huawei:yang:huawei-ospfv3-deviations-NE5000E";
  prefix ospfv3-devs-NE5000E;

  import huawei-ospfv3 {
    prefix ospfv3;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "OSPFv3 management.";

  revision 2019-04-04 {
    description
      "Initial revision.";
    reference "Huawei private.";
  }

  typedef import-rt-protocol-deviations {
    type enumeration {
      enum direct {
        value 1;
        description
          "Direct route.";
      }
      enum ospfv3 {
        value 7;
        description
          "OSPFv3 router.";
      }
      enum isis {
        value 3;
        description
          "ISIS protocol.";
      }
      enum static {
        value 4;
        description
          "Static route.";
      }
      enum ripng {
        value 8;
        description
          "RIPng routes.";
      }
      enum bgp {
        value 6;
        description
          "BGP protocol.";
      }
    }
    description
      "OSPFv3 import route protocol.";
  }

  deviation "/ni:network-instance/ni:instances/ni:instance/ospfv3:ospfv3/ospfv3:sites/ospfv3:site/ospfv3:import-routes/ospfv3:import-route/ospfv3:protocol" {
    deviate replace {
      type ospfv3-devs-NE5000E:import-rt-protocol-deviations;
    }
  }
  deviation "/ni:network-instance/ni:instances/ni:instance/ospfv3:ospfv3/ospfv3:sites/ospfv3:site/ospfv3:spf-control/ospfv3:max-load-balancing" {
    deviate replace {
      type uint32 {
        range "1..64";
      }
      default "64";
    }
  }
  deviation "/ospfv3:ospfv3/ospfv3:advertise-max-cost" {
    deviate not-supported;
  }
  deviation "/ni:network-instance/ni:instances/ni:instance/ospfv3:ospfv3/ospfv3:sites/ospfv3:site/ospfv3:cost-bindings" {
    deviate not-supported;
  }
  deviation "/ni:network-instance/ni:instances/ni:instance/ospfv3:ospfv3/ospfv3:sites/ospfv3:site/ospfv3:bgp-ls" {
    deviate not-supported;
  }
}
