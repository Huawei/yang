/*
Copyright (C) 2019 Huawei Technologies Co., Ltd. All rights reserved.
*/
module huawei-notifications-deviations-NE5000E {
  namespace "urn:huawei:yang:huawei-notifications-deviations-NE5000E";
  prefix ncEvent-devs-NE5000E;

  import notifications {
    prefix ncEvent;
  }

  organization
    "Huawei Technologies Co., Ltd.";
  contact
    "Huawei Industrial Base
     Bantian, Longgang
     Shenzhen 518129
     People's Republic of China
     Website: http://www.huawei.com
     Email: support@huawei.com";
  description
    "Notifications deviation file.";

  revision 2019-06-17 {
    description
      "Initial revision.";
    reference "Huawei private.";
  }

  deviation "/ncEvent:notification" {
    deviate not-supported;
  }
}
