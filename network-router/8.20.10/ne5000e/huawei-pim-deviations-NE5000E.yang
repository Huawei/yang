/*
Copyright (C) 2019 Huawei Technologies Co., Ltd. All rights reserved.
*/
module huawei-pim-deviations-NE5000E {
  yang-version 1;
  namespace "urn:huawei:yang:huawei-pim-deviations-NE5000E";
  prefix pim-devs-NE5000E;

  import huawei-network-instance {
    prefix ni;
  }
  import huawei-pim {
    prefix pim;
  }
  import huawei-l3-multicast {
    prefix l3-multicast;
  }
  import huawei-extension {
    prefix ext;
  }
  import huawei-mvpn {
    prefix mvpn;
  }
  import huawei-l3vpn {
    prefix l3vpn;
  }

  organization
    "Huawei Technologies Co., Ltd.";
  contact
    "Huawei Industrial Base
     Bantian, Longgang
     Shenzhen 518129
     People's Republic of China
     Website: http://www.huawei.com
     Email: support@huawei.com";
  description
    "Protocol Independent Multicast.";

  revision 2019-06-12 {
    description
      "Init revision.";
    reference "Huawei private.";
  }

  deviation "/ni:network-instance/ni:instances/ni:instance/pim:pim/pim:protocol/pim:instances/pim:instance/pim:hello-join-attr-enable" {
    deviate not-supported;
  }
  deviation "/ni:network-instance/ni:instances/ni:instance/pim:pim/pim:protocol/pim:instances/pim:instance/pim:clone-inherit-enable" {
    deviate not-supported;
  }
  deviation "/ni:network-instance/ni:instances/ni:instance/pim:pim/pim:protocol/pim:interfaces/pim:interface/pim:mode" {
    deviate not-supported;
  }
  deviation "/ni:network-instance/ni:instances/ni:instance/pim:pim/pim:protocol/pim:interfaces/pim:interface/pim:ignore-dr" {
    deviate not-supported;
  }
  deviation "/ni:network-instance/ni:instances/ni:instance/pim:pim/pim:protocol/pim:interfaces/pim:interface/pim:ignore-assert" {
    deviate not-supported;
  }
  deviation "/ni:network-instance/ni:instances/ni:instance/pim:pim/pim:protocol/pim:interfaces/pim:interface/pim:single-tag-fwd-enable" {
    deviate not-supported;
  }
  deviation "/ni:network-instance/ni:instances/ni:instance/pim:pim/pim:protocol/pim:interfaces/pim:interface/pim:graft-retry" {
    deviate not-supported;
  }
  deviation "/ni:network-instance/ni:instances/ni:instance/pim:pim/pim:protocol/pim:interfaces/pim:interface/pim:state-refresh-capable" {
    deviate not-supported;
  }
  deviation "/ni:network-instance/ni:instances/ni:instance/pim:pim/pim:protocol/pim:instances/pim:instance/pim:vector" {
    deviate not-supported;
  }
  deviation "/ni:network-instance/ni:instances/ni:instance/pim:pim/pim:protocol/pim:instances/pim:instance/pim:state-refresh-interval" {
    deviate not-supported;
  }
  deviation "/ni:network-instance/ni:instances/ni:instance/pim:pim/pim:protocol/pim:instances/pim:instance/pim:state-refresh-rate-limit" {
    deviate not-supported;
  }
  deviation "/ni:network-instance/ni:instances/ni:instance/pim:pim/pim:protocol/pim:instances/pim:instance/pim:state-refresh-ttl" {
    deviate not-supported;
  }
  deviation "/ni:network-instance/ni:instances/ni:instance/pim:pim/pim:protocol/pim:interfaces/pim:interface/pim:type" {
    deviate add {
      must "(../pim:type = 'ipv4unicast' and ../../../../../l3-multicast:multicast/l3-multicast:ipv4) or (../pim:type = 'ipv6unicast' and ../../../../../l3-multicast:multicast/l3-multicast:ipv6)";
    }
  }
  deviation "/ni:network-instance/ni:instances/ni:instance/pim:pim/pim:protocol/pim:instances/pim:instance/pim:type" {
    deviate add {
      must "(../pim:type = 'ipv4unicast' and ../../../../../l3-multicast:multicast/l3-multicast:ipv4) or (../pim:type = 'ipv6unicast' and ../../../../../l3-multicast:multicast/l3-multicast:ipv6)";
    }
  }
  deviation "/ni:network-instance/ni:instances/ni:instance/pim:pim/pim:protocol/pim:interfaces/pim:interface/pim:is-silent" {
    deviate add {
      must "../pim:is-silent='false' or (../pim:type='ipv4unicast' and ../pim:bfd-enable='false' and ../pim:dr-swt-delay-enable='false') or (../pim:type='ipv6unicast' and ../pim:bfd-enable='false' and ../pim:dr-swt-delay-enable='false')";
    }
  }
  deviation "/ni:network-instance/ni:instances/ni:instance/pim:pim/pim:protocol/pim:interfaces/pim:interface/pim:dr-swt-delay-enable" {
    deviate add {
      must "../pim:dr-swt-delay-enable='false' or (../pim:type='ipv4unicast' and ../pim:is-silent='false') or (../pim:type='ipv6unicast' and ../pim:is-silent='false')";
    }
  }
  deviation "/ni:network-instance/ni:instances/ni:instance/pim:pim/pim:rp/pim:c-bsr-vpns/pim:c-bsr-vpn/pim:hash-len" {
    deviate add {
      must "(../type='ipv4unicast' and 32>=../hash-len) or (../type='ipv6unicast' and 128>=../hash-len)";
    }
  }
  deviation "/ni:network-instance/ni:instances/ni:instance/pim:pim/pim:protocol/pim:instances/pim:instance/pim:fast-reroute" {
    deviate not-supported;
  }
  deviation "/ni:network-instance/ni:instances/ni:instance/pim:pim/pim:protocol/pim:interfaces/pim:interface/pim:if-infos/pim:join-attribute" {
    deviate not-supported;
  }
  deviation "/ni:network-instance/ni:instances/ni:instance/pim:pim/pim:protocol/pim:interfaces/pim:interface/pim:if-infos/pim:non-join-attribute-nbr-sount" {
    deviate not-supported;
  }
  deviation "/ni:network-instance/ni:instances/ni:instance/pim:pim/pim:protocol/pim:interfaces/pim:interface/pim:if-infos/pim:snooping-enable" {
    deviate not-supported;
  }
  deviation "/ni:network-instance/ni:instances/ni:instance/pim:pim/pim:protocol/pim:routings/pim:routing/pim:user-id" {
    deviate not-supported;
  }
  deviation "/ni:network-instance/ni:instances/ni:instance/pim:pim/pim:rp/pim:elected-bsr-rps/pim:elected-bsr-rp/pim:bidir-enable" {
    deviate not-supported;
  }
  deviation "/ni:network-instance/ni:instances/ni:instance/pim:pim/pim:protocol/pim:interfaces/pim:interface/pim:if-infos/pim:offer-interval" {
    deviate not-supported;
  }
  deviation "/ni:network-instance/ni:instances/ni:instance/pim:pim/pim:protocol/pim:interfaces/pim:interface/pim:if-infos/pim:election-robust-count" {
    deviate not-supported;
  }
  deviation "/ni:network-instance/ni:instances/ni:instance/pim:pim/pim:protocol/pim:interfaces/pim:interface/pim:if-infos/pim:backoff-interval" {
    deviate not-supported;
  }
  deviation "/ni:network-instance/ni:instances/ni:instance/pim:pim/pim:protocol/pim:interfaces/pim:interface/pim:nbrs/pim:nbr/pim:bidir-enable" {
    deviate not-supported;
  }
  deviation "/ni:network-instance/ni:instances/ni:instance/pim:pim/pim:protocol/pim:message-statistics/pim:message-statistic/pim:if-message-statistics/pim:if-message-statistic/pim:offer-recv-num" {
    deviate not-supported;
  }
  deviation "/ni:network-instance/ni:instances/ni:instance/pim:pim/pim:protocol/pim:message-statistics/pim:message-statistic/pim:if-message-statistics/pim:if-message-statistic/pim:offer-send-num" {
    deviate not-supported;
  }
  deviation "/ni:network-instance/ni:instances/ni:instance/pim:pim/pim:protocol/pim:message-statistics/pim:message-statistic/pim:if-message-statistics/pim:if-message-statistic/pim:invalid-offer-num" {
    deviate not-supported;
  }
  deviation "/ni:network-instance/ni:instances/ni:instance/pim:pim/pim:protocol/pim:message-statistics/pim:message-statistic/pim:if-message-statistics/pim:if-message-statistic/pim:filtered-offer-num" {
    deviate not-supported;
  }
  deviation "/ni:network-instance/ni:instances/ni:instance/pim:pim/pim:protocol/pim:message-statistics/pim:message-statistic/pim:if-message-statistics/pim:if-message-statistic/pim:pass-recv-num" {
    deviate not-supported;
  }
  deviation "/ni:network-instance/ni:instances/ni:instance/pim:pim/pim:protocol/pim:message-statistics/pim:message-statistic/pim:if-message-statistics/pim:if-message-statistic/pim:pass-send-num" {
    deviate not-supported;
  }
  deviation "/ni:network-instance/ni:instances/ni:instance/pim:pim/pim:protocol/pim:message-statistics/pim:message-statistic/pim:if-message-statistics/pim:if-message-statistic/pim:invalid-pass-num" {
    deviate not-supported;
  }
  deviation "/ni:network-instance/ni:instances/ni:instance/pim:pim/pim:protocol/pim:message-statistics/pim:message-statistic/pim:if-message-statistics/pim:if-message-statistic/pim:filtered-pass-num" {
    deviate not-supported;
  }
  deviation "/ni:network-instance/ni:instances/ni:instance/pim:pim/pim:protocol/pim:message-statistics/pim:message-statistic/pim:if-message-statistics/pim:if-message-statistic/pim:win-recv-num" {
    deviate not-supported;
  }
  deviation "/ni:network-instance/ni:instances/ni:instance/pim:pim/pim:protocol/pim:message-statistics/pim:message-statistic/pim:if-message-statistics/pim:if-message-statistic/pim:win-send-num" {
    deviate not-supported;
  }
  deviation "/ni:network-instance/ni:instances/ni:instance/pim:pim/pim:protocol/pim:message-statistics/pim:message-statistic/pim:if-message-statistics/pim:if-message-statistic/pim:invalid-win-num" {
    deviate not-supported;
  }
  deviation "/ni:network-instance/ni:instances/ni:instance/pim:pim/pim:protocol/pim:message-statistics/pim:message-statistic/pim:if-message-statistics/pim:if-message-statistic/pim:filtered-win-num" {
    deviate not-supported;
  }
  deviation "/ni:network-instance/ni:instances/ni:instance/pim:pim/pim:protocol/pim:message-statistics/pim:message-statistic/pim:if-message-statistics/pim:if-message-statistic/pim:backoff-recv-num" {
    deviate not-supported;
  }
  deviation "/ni:network-instance/ni:instances/ni:instance/pim:pim/pim:protocol/pim:message-statistics/pim:message-statistic/pim:if-message-statistics/pim:if-message-statistic/pim:backoff-send-num" {
    deviate not-supported;
  }
  deviation "/ni:network-instance/ni:instances/ni:instance/pim:pim/pim:protocol/pim:message-statistics/pim:message-statistic/pim:if-message-statistics/pim:if-message-statistic/pim:invalid-backoff-num" {
    deviate not-supported;
  }
  deviation "/ni:network-instance/ni:instances/ni:instance/pim:pim/pim:protocol/pim:message-statistics/pim:message-statistic/pim:if-message-statistics/pim:if-message-statistic/pim:filtered-backoff-num" {
    deviate not-supported;
  }
  ext:deviation-ext "/ni:network-instance/ni:instances/ni:instance/pim:pim/pim:protocol/pim:interfaces/pim:interface" {
    ext:deviate-ext "add" {
      ext:generated-by "system" {
        when '../../../../l3vpn:afs/l3vpn:af/mvpn:mvpn/mvpn:rosen/mvpn:share-group';
        ext:filter "/ifm:ifm/ifm:interfaces/ifm:interface[ifm:name=current()/pim:if-name]/ifm:type='MTunnel'";
        description
          "When a Rosen MVPN share-group is created, the corresponding MTunnel interface automatically creates a PIM instance.";
      }
    }
  }
}
