/*
Copyright (C) 2019 Huawei Technologies Co., Ltd. All rights reserved.
*/
module huawei-rbs-deviations-NE5000E {
  yang-version 1;
  namespace "urn:huawei:yang:huawei-rbs-deviations-NE5000E";
  prefix rbs-devs-NE5000E;

  import huawei-rbs {
    prefix rbs;
  }

  organization
    "Huawei Technologies Co., Ltd.";
  contact
    "Huawei Industrial Base
     Bantian, Longgang
     Shenzhen 518129
     People's Republic of China
     Website: http://www.huawei.com
     Email: support@huawei.com";
  description
    "Remote backup service, providing service backup between the master and backup devices, such as ARP entry backup.";

  revision 2019-04-23 {
    description
      "Initial revision.";
    reference "Huawei private.";
  }

  typedef service-type-deviations {
    type enumeration {
      enum arp {
        value 5;
        description
          "ARP services that can be backed up.";
      }
      enum nd {
        value 32;
        description
          "Nd service that can backed up.";
      }
    }
    description
      "RBP service type.";
  }

  typedef batch-backup-rpc-type-deviations {
    type enumeration {
      enum all {
        value 0;
        description
          "All services that can be batch backed up now.";
      }
      enum arp {
        value 5;
        description
          "ARP services that can be batch backed up.";
      }
      enum nd {
        value 32;
        description
          "ND services that can be batch backed up.";
      }
    }
    description
      "Service type batch backup.";
  }

  deviation "/rbs:batch-backup-now/rbs:input/rbs:service-type" {
    deviate replace {
      type rbs-devs-NE5000E:batch-backup-rpc-type-deviations;
    }
  }
  deviation "/rbs:rbs/rbs:services/rbs:service/rbs:batch-backups" {
    deviate not-supported;
  }
  deviation "/rbs:rbs/rbs:profiles/rbs:profile/rbs:service-types/rbs:service-type/rbs:type" {
    deviate replace {
      type rbs-devs-NE5000E:service-type-deviations;
    }
  }
  deviation "/rbs:rbs/rbs:profiles/rbs:profile/rbs:name" {
    deviate add {
      must "((../rbs:mode='warm' and not (../rbs:service-types/rbs:service-type[rbs:type='nd']) and not (../rbs:service-types/rbs:service-type[rbs:type='arp'])) or (../rbs:mode='hot') or (../rbs:mode='virtual'))";
    }
  }
  deviation "/rbs:rbs/rbs:profiles/rbs:profile/rbs:track-type/rbs:vrrp/rbs:vrrps" {
    deviate add {
      must "((rbs:vrrp[rbs:mac-type='even'] or rbs:vrrp[rbs:mac-type='odd']) and not(../rbs:service-types/rbs:service-type[rbs:type='arp'] or ../rbs:service-types/rbs:service-type[rbs:type='nd'])) or rbs:vrrp[rbs:mac-type='none']";
    }
  }
}
