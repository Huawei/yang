/*
Copyright (C) 2019 Huawei Technologies Co., Ltd. All rights reserved.
*/
module huawei-pbr-notification-deviations-ATN-980B {
  namespace "urn:huawei:yang:huawei-pbr-notification-deviations-ATN-980B";
  prefix pbr-notification-devs-ATN-980B;

  import huawei-pbr-notification {
    prefix pbr-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-pbr-notification module.";

  revision 2019-11-06 {
    description
      "Initial revision.";
    reference
      "Huawei private.";
  }

  deviation "/pbr-notification:xqos-redirect-nexthop-lack-resource-alarm" {
    deviate not-supported;
  }
  deviation "/pbr-notification:xqos-redirect-nexthop-lack-resource-alarm-resume" {
    deviate not-supported;
  }

}
