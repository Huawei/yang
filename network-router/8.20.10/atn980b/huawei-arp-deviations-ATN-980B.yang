/*
Copyright (C) 2020 Huawei Technologies Co., Ltd. All rights reserved.
*/
module huawei-arp-deviations-ATN-980B {
  yang-version 1;
  namespace "urn:huawei:yang:huawei-arp-deviations-ATN-980B";
  prefix arp-devs-ATN-980B;

  import huawei-arp {
    prefix arp;
  }
  import huawei-ifm {
    prefix ifm;
  }
  import huawei-bd {
    prefix bd;
  }

  organization
    "Huawei Technologies Co., Ltd.";
  contact
    "Huawei Industrial Base
     Bantian, Longgang
     Shenzhen 518129
     People's Republic of China
     Website: http://www.huawei.com
     Email: support@huawei.com";
  description
    "Address Resolution Protocol (ARP) management, which includes static ARP configuration, dynamic ARP learning, ARP security configuration, ARP entry query, and packet statistics collection.";

  revision 2020-05-11 {
    description
      "Initial revision.";
    reference "Huawei private.";
  }

  deviation "/arp:arp/arp:global/arp:dfs-backup-rate" {
    deviate not-supported;
  }
  deviation "/arp:arp/arp:global/arp:smart-discover-interval" {
    deviate not-supported;
  }
  deviation "/arp:arp/arp:global/arp:smart-discover-count" {
    deviate not-supported;
  }
  deviation "/arp:arp/arp:global/arp:ipconflict-detect-enable" {
    deviate not-supported;
  }
  deviation "/arp:arp/arp:speed-limits" {
    deviate not-supported;
  }
  deviation "/bd:bd/bd:instances/bd:instance/arp:arp-list/arp:l2proxy-gw-enable" {
    deviate not-supported;
  }
  deviation "/bd:bd/bd:instances/bd:instance/arp:arp-list/arp:broadcast-suppress" {
    deviate not-supported;
  }
  deviation "/ifm:ifm/ifm:interfaces/ifm:interface/arp:arp-entry/arp:smart-discover-enable" {
    deviate not-supported;
  }
  deviation "/ifm:ifm/ifm:interfaces/ifm:interface/arp:arp-port-security/arp:l2-sub-interface/arp:l2proxy-max-num" {
    deviate replace {
      type uint32 {
        range "0..262144";
      }
    }
  }
}
