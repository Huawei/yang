/*
Copyright (C) 2019 Huawei Technologies Co., Ltd. All rights reserved.
*/
module huawei-loopdetect-deviations-ATN-980B {
  namespace "urn:huawei:yang:huawei-loopdetect-deviations-ATN-980B";
  prefix loopdetect-devs-ATN-980B;

  import huawei-loopdetect {
    prefix loopdetect;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-loopdetect module.";

  revision 2019-11-06 {
    description
      "Initial revision.";
    reference
      "Huawei private.";
  }

  deviation "/ifm:ifm/ifm:interfaces/ifm:interface/loopdetect:loopdetect/loopdetect:loop-detect/loopdetect:block-time-type" {
    deviate not-supported;
  }
  deviation "/ifm:ifm/ifm:interfaces/ifm:interface/loopdetect:loopdetect/loopdetect:loop-detect/loopdetect:block-time-value" {
    deviate not-supported;
  }
  deviation "/ifm:ifm/ifm:interfaces/ifm:interface/loopdetect:loopdetect/loopdetect:loop-detect/loopdetect:trigger-down" {
    deviate not-supported;
  }
  deviation "/loopdetect:loopdetect/loopdetect:trigger-detect/loopdetect:global/loopdetect:min-slot-up-time" {
    deviate replace {
      type uint32 {
        range "1..40";
      }
    }
  }
  deviation "/ifm:ifm/ifm:interfaces/ifm:interface/loopdetect:loopdetect/loopdetect:loopback-detect/loopdetect:block-time" {
    deviate replace {
      type uint32 {
        range "5..255";
      }
    }
    deviate replace {
      default "15";
    }
  }

}
