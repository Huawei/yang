/*
Copyright (C) 2019 Huawei Technologies Co., Ltd. All rights reserved.
*/
module huawei-clocksync-phy-deviations-ATN-980B {
  namespace "urn:huawei:yang:huawei-clocksync-phy-deviations-ATN-980B";
  prefix clocksync-phy-devs-ATN-980B;

  import huawei-clocksync-phy {
    prefix clocksync-phy;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-clocksync-phy module.";

  revision 2019-11-06 {
    description
      "Initial revision.";
    reference
      "Huawei private.";
  }

  deviation "/clocksync-phy:clocksync-phy/clocksync-phy:common/clocksync-phy:freq-switch-enable" {
    deviate not-supported;
  }
  deviation "/ifm:ifm/ifm:interfaces/ifm:interface/clocksync-phy:clock-port-sources/clocksync-phy:source/clocksync-phy:esmc-send-disable" {
    deviate not-supported;
  }
  deviation "/ifm:ifm/ifm:interfaces/ifm:interface/clocksync-phy:clock-port-sources/clocksync-phy:source/clocksync-phy:slave-nego-enable" {
    deviate not-supported;
  }
  deviation "/ifm:ifm/ifm:interfaces/ifm:interface/clocksync-phy:clock-port-sources/clocksync-phy:source/clocksync-phy:e1-sabit" {
    deviate not-supported;
  }
  deviation "/clocksync-phy:clocksync-phy/clocksync-phy:common/clocksync-phy:ssm-control-on" {
    deviate replace {
      default "true";
    }
  }
  deviation "/clocksync-phy:clocksync-phy/clocksync-phy:common/clocksync-phy:freq-check-enable" {
    deviate replace {
      default "false";
    }
  }
  deviation "/clocksync-phy:clocksync-phy/clocksync-phy:selection-sources/clocksync-phy:selection/clocksync-phy:source-name" {
    deviate add {
      must "(((/ifm:ifm/ifm:interfaces/ifm:interface[ifm:name=current()]/clocksync-phy:clock-port-sources/clocksync-phy:source/clocksync-phy:sync-enable='true') or ((../source-type='system') and (/clocksync-phy:clocksync-phy/clocksync-phy:external-clock-sources/clocksync-phy:source[clocksync-phy:name=current()]/clocksync-phy:sync-enable='true'))) or (((../source-type='system') and not(/ifm:ifm/ifm:interfaces/ifm:interface[ifm:name=current()]/clocksync-phy:clock-port-sources/clocksync-phy:source/clocksync-phy:priority/clocksync-phy:system=0)) or ((../source-type='system') and not(/clocksync-phy:clocksync-phy/clocksync-phy:external-clock-sources/clocksync-phy:source[clocksync-phy:name=current()]/clocksync-phy:system-priority=0)))) or ((((../mode='manual') or (../mode='force')) and ../source-type='sync2m-1' and not(/clocksync-phy:clocksync-phy/clocksync-phy:external-clock-sources/clocksync-phy:source[clocksync-phy:name=current()])) or (((../mode='manual') or (../mode='force')) and ../source-type='sync2m-2' and not(/clocksync-phy:clocksync-phy/clocksync-phy:external-clock-sources/clocksync-phy:source[clocksync-phy:name=current()])) or ((../source-type='sync2m-1') and not(/ifm:ifm/ifm:interfaces/ifm:interface[ifm:name=current()]/clocksync-phy:clock-port-sources/clocksync-phy:source/clocksync-phy:priority/clocksync-phy:sync2m1=0)) or ((../source-type='sync2m-2') and not(/ifm:ifm/ifm:interfaces/ifm:interface[ifm:name=current()]/clocksync-phy:clock-port-sources/clocksync-phy:source/clocksync-phy:priority/clocksync-phy:sync2m2=0)))";
    }
  }
  deviation "/clocksync-phy:clocksync-phy/clocksync-phy:external-clock-sources/clocksync-phy:source/clocksync-phy:bits-sources/clocksync-phy:signal-type" {
    deviate add {
      must "(../signal-type='2mhz' or ../signal-type='2mbps')";
    }
  }

}
