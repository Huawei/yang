/*
Copyright (C) 2019 Huawei Technologies Co., Ltd. All rights reserved.
*/
module huawei-bras-dhcpv6-server-deviations-ATN-980B {
  namespace "urn:huawei:yang:huawei-bras-dhcpv6-server-deviations-ATN-980B";
  prefix bras-dhcpv6-server-devs-ATN-980B;

  import huawei-bras-dhcpv6-server {
    prefix bras-dhcpv6-server;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-dhcpv6-server module.";

  revision 2019-11-06 {
    description
      "Initial revision.";
    reference
      "Huawei private.";
  }

  deviation "/bras-dhcpv6-server:bras-dhcpv6-server" {
    deviate not-supported;
  }

}
