/*
Copyright (C) 2019 Huawei Technologies Co., Ltd. All rights reserved.
*/
module huawei-bras-ipv6-address-manage-deviations-ATN-980B {
  namespace "urn:huawei:yang:huawei-bras-ipv6-address-manage-deviations-ATN-980B";
  prefix bras-ipv6-address-manage-devs-ATN-980B;

  import huawei-bras-ipv6-address-manage {
    prefix bras-ipv6-address-manage;
  }

  import huawei-bras-ipv4-address-manage {
    prefix bras-ipv4-address-manage;
  }

  import huawei-l3vpn {
    prefix l3vpn;
  }

  import huawei-network-instance {
    prefix ni;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-ipv6-address-manage module.";

  revision 2019-11-06 {
    description
      "Initial revision.";
    reference
      "Huawei private.";
  }

  deviation "/bras-ipv6-address-manage:bras-ipv6-address-manage" {
    deviate not-supported;
  }
  deviation "/ni:network-instance/ni:instances/ni:instance/l3vpn:afs/l3vpn:af/bras-ipv4-address-manage:bas/bras-ipv6-address-manage:ipv6-address-manage" {
    deviate not-supported;
  }

}
