/*
Copyright (C) 2019 Huawei Technologies Co., Ltd. All rights reserved.
*/
module huawei-if-ip-deviations-ATN-980B {
  namespace "urn:huawei:yang:huawei-if-ip-deviations-ATN-980B";
  prefix if-ip-devs-ATN-980B;

  import huawei-if-ip {
    prefix if-ip;
  }
  import huawei-network-instance {
    prefix ni;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2019-05-06 {
    description
      "Init revision.";
    reference "Huawei private.";
  }

  deviation "/ni:network-instance/ni:instances/ni:instance/if-ip:ipv4-ifs/if-ip:ipv4-if/if-ip:address/if-ip:config-address/if-ip:addresses/if-ip:address/if-ip:type" {
    deviate add {
      must "../if-ip:type='sub' and /ifm:ifm/ifm:global/ifm:ipv4-ignore-primary-sub='false' or ../if-ip:type='main'";
    }
  }
  deviation "/ni:network-instance/ni:instances/ni:instance/if-ip:ipv6-if-states/if-ip:ipv6-if-state/if-ip:addresses/if-ip:address/if-ip:is-block" {
    deviate not-supported;
  }
}
