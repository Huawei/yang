/*
Copyright (C) 2020 Huawei Technologies Co., Ltd. All rights reserved.
*/
module huawei-ietf-network-deviations-ATN-980B {
  yang-version 1.1;
  namespace "urn:huawei:yang:huawei-ietf-network-deviations-ATN-980B";
  prefix nw-devs-ATN-980B;

  import ietf-network {
    prefix nw;
  }

  organization
    "Huawei Technologies Co., Ltd.";
  contact
    "Huawei Industrial Base
     Bantian, Longgang
     Shenzhen 518129
     People's Republic of China
     Website: http://www.huawei.com
     Email: support@huawei.com";
  description
    "Deviations for ietf-network model.";

  revision 2020-09-19 {
    description
      "Initial revision.";
    reference "Huawei private.";
  }

  deviation "/nw:networks" {
    deviate not-supported;
  }
}
