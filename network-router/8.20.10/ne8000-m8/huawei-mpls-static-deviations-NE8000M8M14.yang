/*
Copyright (C) 2019 Huawei Technologies Co., Ltd. All rights reserved.
*/
module huawei-mpls-static-deviations-NE8000M8M14 {
  namespace "urn:huawei:yang:huawei-mpls-static-deviations-NE8000M8M14";
  prefix mpls-static-devs-NE8000M8M14;

  import huawei-mpls {
    prefix mpls;
  }
  import huawei-mpls-static {
    prefix mpls-static;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2019-11-14 {
    description
      "Initial revision.";
    reference "Huawei private.";
  }

  deviation "/mpls:mpls/mpls-static:static/mpls-static:lsps/mpls-static:lsp/mpls-static:egress/mpls-static:in-label" {
    deviate replace {
      type uint32 {
        range "16..65551";
      }
    }
  }
  deviation "/mpls:mpls/mpls-static:static/mpls-static:lsps/mpls-static:lsp/mpls-static:transit/mpls-static:in-label" {
    deviate replace {
      type uint32 {
        range "16..65551";
      }
    }
  }
}
