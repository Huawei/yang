/*
Copyright (C) 2019 Huawei Technologies Co., Ltd. All rights reserved.
*/
module huawei-trafficmng-deviations-NE8000M8M14 {
  namespace "urn:huawei:yang:huawei-trafficmng-deviations-NE8000M8M14";
  prefix trafficmng-devs-NE8000M8M14;

  import huawei-trafficmng {
    prefix trafficmng;
  }

  organization
    "Huawei Technologies Co., Ltd.";

  contact
    "Huawei Industrial Base
     Bantian, Longgang
     Shenzhen 518129
     People's Republic of China
     Website: http://www.huawei.com
     Email: support@huawei.com";

  description
    "This module defines deviation statements for huawei-trafficmng module.";

  revision 2019-11-06 {
    description
      "Initial revision.";
    reference
      "Huawei private.";
  }

  deviation "/trafficmng:trafficmng/trafficmng:board-alarm-sfu-thresholds" {
    deviate not-supported;
  }
  deviation "/trafficmng:trafficmng/trafficmng:board-alarm-lpu-thresholds" {
    deviate not-supported;
  }
  deviation "/trafficmng:trafficmng/trafficmng:sfu-warm-backup-switch" {
    deviate not-supported;
  }
  deviation "/trafficmng:trafficmng/trafficmng:packet-loss-alarms" {
    deviate not-supported;
  }
  deviation "/trafficmng:trafficmng/trafficmng:lpu-backpressure-switch" {
    deviate not-supported;
  }
  deviation "/trafficmng:trafficmng/trafficmng:tm-sfu-informations" {
    deviate not-supported;
  }
  deviation "/trafficmng:trafficmng/trafficmng:tm-lpu-statuss/trafficmng:tm-lpu-status/trafficmng:inbound-switch-port-statuss" {
    deviate not-supported;
  }
  deviation "/trafficmng:trafficmng/trafficmng:tm-lpu-statuss/trafficmng:tm-lpu-status/trafficmng:outbound-switch-port-statuss" {
    deviate not-supported;
  }

}
