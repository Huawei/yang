/*
Copyright (C) 2019 Huawei Technologies Co., Ltd. All rights reserved.
*/
module huawei-wdm-deviations-NE8000M8M14 {
  namespace "urn:huawei:yang:huawei-wdm-deviations-NE8000M8M14";
  prefix wdm-devs-NE8000M8M14;

  import huawei-wdm {
    prefix wdm;
  }

  organization
    "Huawei Technologies Co., Ltd.";

  contact
    "Huawei Industrial Base
     Bantian, Longgang
     Shenzhen 518129
     People's Republic of China
     Website: http://www.huawei.com
     Email: support@huawei.com";

  description
    "This module defines deviation statements for huawei-wdm module.";

  revision 2019-11-06 {
    description
      "Initial revision.";
    reference
      "Huawei private.";
  }

  deviation "/wdm:wdm/wdm:wdms/wdm:wdm/wdm:otn-port-alarm-status" {
    deviate not-supported;
  }

}
