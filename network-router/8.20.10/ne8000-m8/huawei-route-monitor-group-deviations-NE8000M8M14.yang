/*
Copyright (C) 2019 Huawei Technologies Co., Ltd. All rights reserved.
*/
module huawei-route-monitor-group-deviations-NE8000M8M14 {
  namespace "urn:huawei:yang:huawei-route-monitor-group-deviations-NE8000M8M14";
  prefix rmg-devs-NE8000M8M14;

  import huawei-route-monitor-group {
    prefix rmg;
  }

  organization
    "Huawei Technologies Co., Ltd.";
  contact
    "Huawei Industrial Base
     Bantian, Longgang
     Shenzhen 518129
     People's Republic of China
     Website: http://www.huawei.com
     Email: support@huawei.com";
  description
    "A route monitoring group monitors the status of its member routes.";

  revision 2019-04-27 {
    description
      "Initial revision.";
    reference "Huawei private.";
  }

  deviation "/rmg:route-monitor-group/rmg:monitor-groups/rmg:monitor-group/rmg:operator-and" {
    deviate not-supported;
  }
  deviation "/rmg:route-monitor-group/rmg:monitor-groups/rmg:monitor-group/rmg:trigger-down-delay" {
    deviate not-supported;
  }
}
