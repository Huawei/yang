/*
Copyright (C) 2019 Huawei Technologies Co., Ltd. All rights reserved.
*/
module huawei-cpudefend-notification-deviations-NE8000M8M14 {
  namespace "urn:huawei:yang:huawei-cpudefend-notification-deviations-NE8000M8M14";
  prefix cpudefend-notification-devs-NE8000M8M14;

  import huawei-cpudefend-notification {
    prefix cpudefend-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-cpudefend-notification module.";

  revision 2019-11-06 {
    description
      "Initial revision.";
    reference
      "Huawei private.";
  }

  deviation "/cpudefend-notification:portcar-alarm" {
    deviate not-supported;
  }
  deviation "/cpudefend-notification:portcar-alarm-clear" {
    deviate not-supported;
  }
  deviation "/cpudefend-notification:arpvlancar-alarm" {
    deviate not-supported;
  }
  deviation "/cpudefend-notification:arpvlancar-alarm-clear" {
    deviate not-supported;
  }

}
