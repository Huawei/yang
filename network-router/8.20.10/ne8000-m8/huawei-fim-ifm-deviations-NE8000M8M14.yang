/*
Copyright (C) 2019 Huawei Technologies Co., Ltd. All rights reserved.
*/
module huawei-fim-ifm-deviations-NE8000M8M14 {
  namespace "urn:huawei:yang:huawei-fim-ifm-deviations-NE8000M8M14";
  prefix fim-ifm-devs-NE8000M8M14;

  import huawei-fim-ifm {
    prefix fim-ifm;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-fim-ifm module.";

  revision 2019-11-06 {
    description
      "Initial revision.";
    reference
      "Huawei private.";
  }

  deviation "/ifm:ifm/ifm:interfaces/ifm:interface/fim-ifm:fim-ifm-veint/fim-ifm:ve-slot-id" {
    deviate not-supported;
  }
  deviation "/ifm:ifm/ifm:global/fim-ifm:fim-trunk-localfwd" {
    deviate not-supported;
  }

}
