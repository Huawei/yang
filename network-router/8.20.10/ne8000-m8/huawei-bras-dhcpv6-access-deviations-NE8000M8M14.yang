/*
Copyright (C) 2019 Huawei Technologies Co., Ltd. All rights reserved.
*/
module huawei-bras-dhcpv6-access-deviations-NE8000M8M14 {
  namespace "urn:huawei:yang:huawei-bras-dhcpv6-access-deviations-NE8000M8M14";
  prefix bras-dhcpv6-access-devs-NE8000M8M14;

  import huawei-bras-dhcpv6-access {
    prefix bras-dhcpv6-access;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-dhcpv6-access module.";

  revision 2019-11-06 {
    description
      "Initial revision.";
    reference
      "Huawei private.";
  }

  deviation "/devm:devm/devm:lpu-boards/devm:lpu-board/bras-dhcpv6-access:dhcpv6-access" {
    deviate not-supported;
  }

}
