/*
Copyright (C) 2019-2020 Huawei Technologies Co., Ltd. All rights reserved.
*/
module huawei-mac-flapping {
  namespace "urn:huawei:yang:huawei-mac-flapping";
  prefix mac-flapping;
  import huawei-ifm {
    prefix ifm;
  }
  import huawei-ethernet {
    prefix ethernet;
  }
  import huawei-bd {
    prefix bd;
  }
  import huawei-vlan {
    prefix vlan;
  }
  import huawei-l2vpn {
    prefix l2vpn;
  }
  import huawei-extension {
    prefix ext;
  }  
  organization
    "Huawei Technologies Co., Ltd.";
  contact
    "Huawei Industrial Base
     Bantian, Longgang
     Shenzhen 518129
     People's Republic of China
     Website: http://www.huawei.com
     Email: support@huawei.com";
  description
    "MAC flapping-based loop detection.";
  revision 2020-03-09 {
    description
      "Modify description.";
    reference
      "Huawei private.";
  }
  revision 2019-04-23 {
    description
      "Initial revision.";
    reference
      "Huawei private.";
  }
  ext:task-name  "mflp"; 
  typedef alarm-enable {
    type enumeration {
      enum "block" {
        value 1;	  
        description
          "Disable the loop detection alarm function.";
      }
      enum "alarm" {
        value 2;	  
        description
          "Enable the loop detection alarm function.";
      }
    }
    description
      "Alarm enable.";
  } 
  typedef mflp-enable {
    type enumeration {
      enum "disable" {
        value 1;
        description
          "Disable type.";
      }
      enum "enable" {
        value 2;
        description
          "Enable type.";
      }
    }
    description
      "MFLP enable type.";
  }
  grouping group-mac-flapping {
    description
      "Configuration of MAC flapping.";
    container mac-flapping {
      description
        "Configure MAC flapping.";
      container loop-detect{
        presence "Loop detect configuration.";
        description
          "Configure VSI MAC flapping entry.";
        leaf loop-times {
          type uint32 {
            range "3..1000";
          }
          mandatory true;
          description
            "Number of MAC address flappings.";
        }
        leaf detect-cycle {
          type uint32 {
            range "3..30";
          }
          units s;
          mandatory true;
          description
            "Detection cycle.";
        }
        leaf cycles {
          type uint32 {
            range "1..15";
          }
          mandatory true;
          description
            "Number of cycles.";
        }
        leaf action {
          type alarm-enable;
          mandatory true;
          description
            "Action taken after a loop occurs. The action can be reporting an alarm or blocking an interface.";
        }
        leaf retry-times {
          when "../action='block'";
          type uint32 {
            range "0..5";
          }
          must "(../retry-times and ../block-time) or (not(../retry-times) and not(../block-time))";
          description
            "Retry times.";
        }
        leaf block-time {
          when "../action='block'";
          type uint32 {
            range "10..65535";
          }
          units s;
          must "(../retry-times and ../block-time) or (not(../retry-times) and not(../block-time))";
          description
            "Blocking time.";
        }
      }
      container precise-block {
        presence "precise-block";
        description
          "Configure precise blocking policy table.";
      }
    }
  }
  container mac-flapping {
    description
      "MAC flapping-based loop detection.";
    container global-attribute {
      description
        "Configure global attribute of MFLP.";
      leaf precise-block-policy {
        type mflp-enable;
        default "disable";
        description
          "Global blocking policy.";
      }
      leaf generate-time {
        type uint32 {
          range "60..2000000";
        }
        units s;
        default "600";
        description
          "Trust interface generation time.";
      }
      leaf assist-stp {
        type mflp-enable;
        default "disable";
        description
          "MAC flapping assist flag.";
      }
      leaf traffic-suppression {
        type mflp-enable;
        default "enable";
        description
          "Global traffic suppress state.";
      }
      leaf traffic-suppression-threshold {
        type uint16 {
          range "10..50";
        }
        units %;
        default "10";
        description
          "Traffic suppress threshold.";
      }    
    }
  }
  augment "/l2vpn:l2vpn/l2vpn:instances/l2vpn:instance/l2vpn:vpls" {
    description
      "MAC flapping patameters on VSI.";  
    uses group-mac-flapping {
      refine mac-flapping/precise-block {
        must "../../l2vpn:work-mode='normal'";
      }
    }
  }
  augment "/bd:bd/bd:instances/bd:instance" {
    description
      "MAC flapping patameters on BD.";
    uses group-mac-flapping {
      refine mac-flapping/loop-detect {
        description
          "Configure BD MAC flapping entry.";
      }
    }
  }
  augment "/vlan:vlan/vlan:vlans/vlan:vlan" {
    description
      "MAC flapping patameters on VLAN.";
    uses group-mac-flapping {
      refine mac-flapping/loop-detect {
        description
          "Configure VLAN MAC flapping entry.";
      }
    }
  }
  augment "/ifm:ifm/ifm:interfaces/ifm:interface/ethernet:ethernet/ethernet:main-interface" {
    description
      "MAC flapping patameters on the interface.";
    container mflp-mac-shift{
      presence "mflp mac shift";
      description
        "Configure MAC flapping-based loop detection association on an interface.";
    }
  }
}
