/*
Copyright (C) 2020 Huawei Technologies Co., Ltd. All rights reserved.
*/
module huawei-ifm-trunk-notification {
  yang-version 1;
  namespace "urn:huawei:yang:huawei-ifm-trunk-notification";
  prefix ifm-trunk-notification;
  import huawei-pub-type {
    prefix pub-type;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of ifm-trunk.";
  revision 2020-08-12 {
    description
      "Initial revision.";
    reference
      "Huawei private.";
  }
  ext:task-name "trunk";
  typedef port-status {
    type enumeration {
      enum "up" {
        value 1;
        description
          "The interface is in Up state.";
      }
      enum "down" {
        value 2;
        description
          "The interface is in Down state.";
      }
    }
    description
      "Interface suppression status.";
  }
  notification all-member-down {
    description
      "The last member interface link status changes to down.";
    leaf trunk-index {
      type uint32;
      mandatory true;
      description
        "Trunk interface index.";
    }
    leaf trunk-name {
      type pub-type:if-name;
      mandatory true;
      description
        "Name of the Trunk interface.";
    }
  }
  notification all-member-down-resume {
    description
      "The first member interface link status changes to up.";
    leaf trunk-index {
      type uint32;
      mandatory true;
      description
        "Trunk interface index.";
    }
    leaf trunk-name {
      type pub-type:if-name;
      mandatory true;
      description
        "Name of the Trunk interface.";
    }
  }
  notification all-member-up {
    description
      "All member links of the trunk went Up.";
    leaf trunk-name {
      type pub-type:if-name;
      mandatory true;
      description
        "Name of the trunk interface.";
    }
  }
  notification member-link-down {
    description
      "A trunk member interface went Down.";
    leaf port-index {
      type uint32;
      mandatory true;
      description
        "Index of a trunk member interface.";
    }
    leaf member-admin-status {
      type uint32;
      mandatory true;
      description
        "Administration status of a trunk member interface.";
    }
    leaf member-oper-status {
      type uint32;
      mandatory true;
      description
        "Operating status of a trunk member interface.";
    }
    leaf port-name {
      type pub-type:if-name;
      mandatory true;
      description
        "Name of a trunk member interface.";
    }
    leaf member-phy-status {
      type uint32;
      mandatory true;
      description
        "Physical status of a trunk member interface.";
    }
    leaf trunk-index {
      type uint32;
      mandatory true;
      description
        "Index of the trunk interface to which the member interface belongs.";
    }
    leaf trunk-name {
      type pub-type:if-name;
      mandatory true;
      description
        "Name of the trunk interface to which the member interface belongs.";
    }
  }
  notification member-link-up {
    description
      "A trunk member interface went Up.";
    leaf port-index {
      type uint32;
      mandatory true;
      description
        "Index of a trunk member interface.";
    }
    leaf member-admin-status {
      type uint32;
      mandatory true;
      description
        "Administration status of a trunk member interface.";
    }
    leaf member-oper-status {
      type uint32;
      mandatory true;
      description
        "Operating status of a trunk member interface.";
    }
    leaf port-name {
      type pub-type:if-name;
      mandatory true;
      description
        "Name of a trunk member interface.";
    }
    leaf member-phy-status {
      type uint32;
      mandatory true;
      description
        "Physical status of a trunk member interface.";
    }
    leaf trunk-index {
      type uint32;
      description
        "Index of a trunk interface.";
    }
    leaf trunk-name {
      type pub-type:if-name;
      mandatory true;
      description
        "Name of the trunk interface to which the member interface belongs.";
    }
  }
  notification member-number-change {
    description
      "The number of active trunk member interfaces changed.";
    leaf trunk-name {
      type pub-type:if-name;
      mandatory true;
      description
        "Name of the trunk interface.";
    }
    leaf port-name {
      type pub-type:if-name;
      mandatory true;
      description
        "Name of the trunk member interface.";
    }
    leaf trunk-mem-number {
      type uint32;
      mandatory true;
      description
        "Number of active trunk member interfaces.";
    }
    leaf reason {
      type string {
        length "0..127";
      }
      mandatory true;
      description
        "Reason.";
    }
  }
  notification trunk-status-change {
    description
      "The trunk interface status changes.";
    leaf trunk-name {
      type pub-type:if-name;
      mandatory true;
      description
        "Name of the trunk interface.";
    }
    leaf trunk-index {
      type uint32;
      mandatory true;
      description
        "Trunk index.";
    }
    leaf trunk-admin-status {
      type port-status;
      mandatory true;
      description
        "Administration status of trunk interface.";
    }
    leaf trunk-status {
      type port-status;
      mandatory true;
      description
        "Status of trunk interface.";
    }
  }
  notification trunk-bandwidth-change {
    description
      "The trunk interface bandwidth changes.";
    leaf trunk-name {
      type pub-type:if-name;
      mandatory true;
      description
        "Name of the trunk interface.";
    }
    leaf old-bandwidth {
      type uint64;
      units "bit/s";
      mandatory true;
      description
        "Old bandwidth of the trunk interface.";
    }
    leaf new-bandwidth {
      type uint64;
      units "bit/s";
      mandatory true;
      description
        "New bandwidth of the trunk interface.";
    }
  }
}
