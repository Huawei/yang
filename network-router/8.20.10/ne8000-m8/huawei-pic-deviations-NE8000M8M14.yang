/*
Copyright (C) 2019 Huawei Technologies Co., Ltd. All rights reserved.
*/
module huawei-pic-deviations-NE8000M8M14 {
  namespace "urn:huawei:yang:huawei-pic-deviations-NE8000M8M14";
  prefix pic-devs-NE8000M8M14;

  import huawei-pic {
    prefix pic;
  }

  import huawei-extension {
    prefix ext;
  }

  import huawei-driver {
    prefix driver;
  }

  import huawei-devm {
    prefix devm;
  }

  import huawei-license {
    prefix lcs;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic module.";

  revision 2019-11-06 {
    description
      "Initial revision.";
    reference
      "Huawei private.";
  }

  typedef alarm-ais-insert-name-deviations {
    type enumeration {
      enum "hptim" {
        value 1;
        description 
          "Hptim.";
      }
      enum "lptim" {
        value 2;
        description 
          "Lptim.";
      }
      enum "rstim" {
        value 3;
        description 
          "Rstim.";
      }
      enum "hpuneq" {
        value 6;
        description 
          "Hpuneq.";
      }
      enum "hpplm" {
        value 7;
        description 
          "Hpplm.";
      }
      enum "lpuneq" {
        value 8;
        description 
          "Lpuneq.";
      }
    }
    description 
      "Alarm Name.";
  }

  typedef auto-clear-deviations {
    type enumeration {
      enum "physical-mode" {
        value 14;
        description 
          "Physical mode.";
      }
    }
    description 
      "Auto Clear Type.";
  }

  typedef card-bandmode-deviations {
    type enumeration {
      enum "POS-8X622M" {
        value 12;
        description 
          "Eight 622M POS port.";
      }
      enum "POS-8X155M" {
        value 15;
        description 
          "Eight 155M POS port.";
      }
    }
    description 
      "Bandwidth Mode. Modifying the configuration affects the instances of ports and interfaces. For details about the impact, see the description of each enumerated item.";
  }

  typedef clock-deviations {
    type enumeration {
      enum "master" {
        value 0;
        description 
          "Master.";
      }
      enum "slave" {
        value 1;
        description 
          "Slave.";
      }
    }
    default "master";
    description 
      "Clock mode.";
  }

  typedef eth-speed-type-deviations {
    type enumeration {
      enum "10M" {
        value 0;
        description 
          "Configure 10M.";
      }
      enum "100M" {
        value 1;
        description 
          "Configure 100M.";
      }
      enum "1000M" {
        value 2;
        description 
          "Configure 1000M.";
      }
      enum "auto" {
        value 9;
        description 
          "Auto.";
      }
    }
    description 
      "Speed type.";
  }

  typedef port-negotiation-mode-type-deviations {
    type enumeration {
      enum "slave" {
        value 0;
        description 
          "Slave.";
      }
    }
    description 
      "Port negotiation mode.";
  }

  deviation "/driver:driver/driver:global-attribute/pic:global/pic:port-down-laser-shut-log-enable" {
    deviate not-supported;
  }
  deviation "/devm:devm/devm:ports/devm:port/pic:ethernet/pic:mru" {
    deviate not-supported;
  }
  deviation "/devm:devm/devm:ports/devm:port/pic:ethernet/pic:inter-packet-gap" {
    deviate not-supported;
  }
  deviation "/devm:devm/devm:ports/devm:port/pic:ethernet/pic:mac-itf-mode" {
    deviate not-supported;
  }
  deviation "/devm:devm/devm:ports/devm:port/pic:ethernet/pic:attenuation" {
    deviate not-supported;
  }
  deviation "/devm:devm/devm:ports/devm:port/pic:ethernet/pic:remote-fault" {
    deviate not-supported;
  }
  deviation "/devm:devm/devm:ports/devm:port/pic:ethernet/pic:los-trap-down-hold" {
    deviate not-supported;
  }
  deviation "/devm:devm/devm:ports/devm:port/pic:optical-module/pic:vendor-oui" {
    deviate not-supported;
  }
  deviation "/devm:devm/devm:ports/devm:port/pic:optical-module/pic:vendor-rev" {
    deviate not-supported;
  }
  deviation "/devm:devm/devm:ports/devm:port/pic:optical-module/pic:gpon-sn" {
    deviate not-supported;
  }
  deviation "/devm:devm/devm:ports/devm:port/pic:transmission-alarm/pic:threshold-bip2tca" {
    deviate not-supported;
  }
  deviation "/devm:devm/devm:ports/devm:port/pic:pos/pic:frame-format" {
    deviate not-supported;
  }
  deviation "/devm:devm/devm:ports/devm:port/pic:pos/pic:speed" {
    deviate not-supported;
  }
  deviation "/devm:devm/devm:ports/devm:port/pic:atm" {
    deviate not-supported;
  }
  deviation "/devm:devm/devm:ports/devm:port/pic:cpos/pic:e1t1s/pic:e1t1/pic:clock-recovery-domain" {
    deviate not-supported;
  }
  deviation "/devm:devm/devm:ports/devm:port/pic:cpos/pic:e1t1s/pic:e1t1/pic:clock-master-domain" {
    deviate not-supported;
  }
  deviation "/devm:devm/devm:ports/devm:port/pic:port-alarm/pic:alarm-type/pic:crc-error-threshold/pic:crc-error-threshold/pic:crc-error" {
    deviate not-supported;
  }
  deviation "/devm:devm/devm:ports/devm:port/pic:port-alarm/pic:alarm-type/pic:link-crc/pic:crc-per-warn" {
    deviate not-supported;
  }
  deviation "/devm:devm/devm:ports/devm:port/pic:adm-port" {
    deviate not-supported;
  }
  deviation "/devm:devm/devm:ports/devm:port/pic:e1t1/pic:code" {
    deviate not-supported;
  }
  deviation "/devm:devm/devm:ports/devm:port/pic:e1t1/pic:bipv-static" {
    deviate not-supported;
  }
  deviation "/devm:devm/devm:ports/devm:port/pic:e1t1/pic:fas-static" {
    deviate not-supported;
  }
  deviation "/devm:devm/devm:ports/devm:port/pic:e1t1/pic:crc-static" {
    deviate not-supported;
  }
  deviation "/devm:devm/devm:ports/devm:port/pic:e3t3" {
    deviate not-supported;
  }
  deviation "/lcs:license/pic:lcs-ports/pic:port-basic/pic:port-band" {
    deviate not-supported;
  }
  deviation "/lcs:license/pic:upgrade-ports" {
    deviate not-supported;
  }
  deviation "/lcs:license/pic:flexe-ports" {
    deviate not-supported;
  }
  deviation "/lcs:license/pic:expand-ports" {
    deviate not-supported;
  }
  deviation "/lcs:license/pic:rtus" {
    deviate not-supported;
  }
  deviation "/lcs:license/pic:rtu-extends" {
    deviate not-supported;
  }
  deviation "/devm:devm/devm:cards/devm:card/pic:service-mode/pic:portrate" {
    deviate not-supported;
  }
  deviation "/devm:devm/devm:cards/devm:card/pic:queue-priority" {
    deviate not-supported;
  }
  deviation "/devm:devm/devm:cards/devm:card/pic:frame-format" {
    deviate not-supported;
  }
  deviation "/devm:devm/devm:cards/devm:card/pic:process-mode" {
    deviate not-supported;
  }
  deviation "/devm:devm/devm:mpu-boards/devm:mpu-board/pic:cmac-padding" {
    deviate not-supported;
  }
  deviation "/devm:devm/devm:lpu-boards/devm:lpu-board/pic:cmac-padding" {
    deviate not-supported;
  }
  deviation "/pic:pic/pic:auto-clears/pic:auto-clear/pic:type" {
    deviate replace {
      type pic-devs-NE8000M8M14:auto-clear-deviations;
    }
  }
  ext:deviation-ext "/pic:pic/pic:auto-clears/pic:auto-clear/pic:time" {
    ext:deviate-ext replace {
      ext:dynamic-default {
        ext:default-value "20" {
          when "../type = 'physical-mode'";
          description "The default value is 20 when type is physical-mode.";
        }
      }
    }
  }
  deviation "/pic:pic/pic:alarm-ais-inserts/pic:alarm-ais-insert/pic:name" {
    deviate replace {
      type pic-devs-NE8000M8M14:alarm-ais-insert-name-deviations;
    }
  }
  deviation "/pic:pic/pic:alarm-ais-inserts/pic:alarm-ais-insert/pic:ais" {
    deviate add {
      must "(../name = 'lpuneq' and ../ais = 'false') or (../name = 'hptim' or ../name = 'lptim' or ../name = 'rstim' or ../name = 'hpuneq' or ../name = 'hpplm')";
    }
  }
  deviation "/pic:pic/pic:alarm-ais-inserts/pic:alarm-ais-insert/pic:rdi" {
    deviate add {
      must "((../name = 'rstim' or ../name = 'hpuneq' or ../name = 'hpplm') and ../rdi = 'false') or (../name = 'hptim' or ../name = 'lptim' or ../name = 'lpuneq')";
    }
  }
  ext:deviation-ext "/pic:pic/pic:alarm-ais-inserts/pic:alarm-ais-insert/pic:rdi" {
    ext:deviate-ext add {
      ext:dynamic-default {
        ext:default-value "false" {
          when "../name = 'hpuneq' or ../name = 'hpplm' or ../name = 'lpuneq' or ../name = 'hptim' or ../name = 'lptim' or ../name = 'rstim'";
          description "The default value is false when name is hpuneq or hpplm or lpuneq or hptim or lptim or rstim.";
        }
      }
    }
  }
  deviation "/devm:devm/devm:ports/devm:port/pic:ethernet/pic:speed" {
    deviate replace {
      type pic-devs-NE8000M8M14:eth-speed-type-deviations;
    }
  }
  deviation "/devm:devm/devm:ports/devm:port/pic:ethernet/pic:negotiation-mode" {
    deviate replace {
      type pic-devs-NE8000M8M14:port-negotiation-mode-type-deviations;
    }
  }
  deviation "/devm:devm/devm:ports/devm:port/pic:cpos/pic:e1t1s/pic:e1t1/pic:clock" {
    deviate replace {
      type pic-devs-NE8000M8M14:clock-deviations;
    }
  }
  deviation "/devm:devm/devm:ports/devm:port/pic:cpos/pic:e1t1s/pic:e1t1/pic:loopback" {
    deviate add {
      must "(../clock='master' and (../loopback='none' or ../loopback='local')) or (../clock='slave' and (../loopback='none' or ../loopback='remote'))";
    }
  }
  deviation "/devm:devm/devm:ports/devm:port/pic:port-alarm/pic:alarm-type/pic:crc-error-threshold/pic:crc-error-threshold/pic:crc-error-interval" {
    deviate add {
      must "not(../crc-error-percent-alm-thr)";
    }
  }
  deviation "/devm:devm/devm:ports/devm:port/pic:port-alarm/pic:alarm-type/pic:link-crc/pic:crc-per-alarm/pic:crc-per-alm-thr-power" {
    deviate replace {
      type uint32 {
        range "1..5";
      }
    }
  }
  deviation "/devm:devm/devm:ports/devm:port/pic:port-alarm/pic:alarm-type/pic:link-crc/pic:crc-per-alarm/pic:crc-per-rsum-thr-power" {
    deviate replace {
      type uint32 {
        range "1..6";
      }
    }
  }
  deviation "/devm:devm/devm:cards/devm:card/pic:service-mode/pic:bandwidth-mode" {
    deviate replace {
      type pic-devs-NE8000M8M14:card-bandmode-deviations;
    }
  }

}
