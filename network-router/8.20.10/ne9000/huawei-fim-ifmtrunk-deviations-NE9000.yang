/*
Copyright (C) 2019 Huawei Technologies Co., Ltd. All rights reserved.
*/
module huawei-fim-ifmtrunk-deviations-NE9000 {
  namespace "urn:huawei:yang:huawei-fim-ifmtrunk-deviations-NE9000";
  prefix fim-ifmtrunk-devs-NE9000;

  import huawei-fim-ifmtrunk {
    prefix fim-ifmtrunk;
  }

  import huawei-ifm {
    prefix ifm;
  }

  import huawei-ifm-trunk {
    prefix ifm-trunk;
  }

  organization
    "Huawei Technologies Co., Ltd.";

  contact
    "Huawei Industrial Base
     Bantian, Longgang
     Shenzhen 518129
     People's Republic of China
     Website: http://www.huawei.com
     Email: support@huawei.com";

  description
    "This module defines deviation statements for huawei-fim-ifmtrunk module.";

  revision 2019-11-06 {
    description
      "Initial revision.";
    reference
      "Huawei private.";
  }

  deviation "/ifm:ifm/ifm:interfaces/ifm:interface/ifm-trunk:trunk/fim-ifmtrunk:fim-ifmtrunk/fim-ifmtrunk:trunk-hash-type" {
    deviate not-supported;
  }

}
