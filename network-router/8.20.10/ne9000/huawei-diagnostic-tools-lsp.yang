/*
Copyright (C) 2019 Huawei Technologies Co., Ltd. All rights reserved.
*/
submodule huawei-diagnostic-tools-lsp {
  yang-version 1;
  belongs-to huawei-diagnostic-tools {
    prefix diagnostic-tools;
  }

  import huawei-pub-type {
    prefix pub-type;
  }
  import ietf-inet-types {
    prefix inet;
  }
  import huawei-extension {
    prefix ext;
  }
  include huawei-diagnostic-tools-common;
  include huawei-diagnostic-tools-type;

  organization
    "Huawei Technologies Co., Ltd.";
  contact
    "Huawei Industrial Base
     Bantian, Longgang
     Shenzhen 518129
     People's Republic of China
     Website: http://www.huawei.com
     Email: support@huawei.com";
  description
    "Lsp diagnosis tool.";
  revision 2019-04-09 {
    description
      "Initial revision.";
    reference
      "Huawei private.";
  }

  grouping lsp-ping-trace-result-type {
    description
      "Lsp ping trace test result.";
    container ping-results {
      config false;
      description
        "List of ping test results.";
      list ping-result {
        key "test-name path-index";
        config false;
        description
          "Statistics of ping test result.";
        leaf test-name {
          type string {
            length "1..32";
          }
          config false;
          description
            "Test name.";
        }
        leaf path-index {
          type uint32;
          config false;
          description
            "Index Of path.";
        }
        leaf tunnel-name {
          type string {
            length "1..33";
          }
          config false;
          status deprecated;
          description
            "Name of the TE tunnel created by RSVP signaling. This option is available when LSP Type is set to TE Tunnel.";
        }
        leaf packet-send {
          type uint32;
          config false;
          description
            "Total number of sent packets.";
        }
        leaf packet-recv {
          type uint32;
          config false;
          description
            "Total number of received packets.";
        }
        leaf loss-ratio {
          type pub-type:percent {
                range "0..100";
              }
          units "%";
          config false;
          description
            "Packet loss ratio of a test.";
        }
        leaf rtt-min {
          type uint32;
          units "ms";
          config false;
          description
            "Minimum RTT of all test packets.";
        }
        leaf rtt-max {
          type uint32;
          units "ms";
          config false;
          description
            "Maximum RTT of all test packets.";
        }
        leaf rtt-average {
          type uint32;
          units "ms";
          config false;
          description
            "Average RTT of all test packets.";
        }
        leaf status {
          type dgntl-test-status-type;
          config false;
          description
            "Test status.";
        }
        leaf error-type {
          type dgntl-error-type;
          config false;
          status deprecated;
          description
            "Test operation status.";
        }
        container ping-result-details {
          config false;
          description
            "List of ping results of all packets in a test.";
          list ping-result-detail {
            key "index";
            config false;
            description
              "Statistics of ping result of a single packet in a test.";
            leaf index {
              type uint32;
              config false;
              description
                "Serial number of a test packet received by a certain hop.";
            }
            leaf dest-ip-addr {
              type inet:ipv4-address-no-zone;
              config false;
              description
                "Destination address of the related hop in a test.";
            }
            leaf packet-size {
              type uint32;
              config false;
              description
                "Number of bytes in a received response packet.";
            }
            leaf rtt {
              type uint32;
              units "ms";
              config false;
              description
                "RTT of test packets.";
            }
            leaf ttl {
              type uint8 {
                range "1..255";
              }
              config false;
              description
                "TTL of received response packets.";
            }
            leaf ret-code {
              type uint32;
              config false;
              description
                "Return code.";
            }
            leaf sub-code {
              type uint32;
              config false;
              description
                "Return sub-code.";
            }
            leaf result-type {
              type detail-result-type;
              config false;
              description
                "Result of packet sending, which is either success or timeout.";
            }
            leaf is-delete {
              ext:support-filter "true";
              type boolean;
              config false;
              description
                "Enable/disable the function of deleting test results.";
            }
          }
        }
      }
    }
    container trace-results {
      config false;
      description
        "List of trace results.";
      list trace-result {
        key "test-name path-index";
        config false;
        description
          "Statistics of trace result.";
        leaf test-name {
          type string {
            length "1..32";
          }
          config false;
          description
            "Test name.";
        }
        leaf path-index {
          type uint32;
          config false;
          description
            "Index Of path.";
        }
        leaf tunnel-name {
          type string {
            length "1..33";
          }
          config false;
          status deprecated;
          description
            "Name of the TE tunnel created by RSVP signaling. This parameter is available when LSP Type is set to TE Tunnel.";
        }
        leaf status {
          type dgntl-test-status-type;
          config false;
          description
            "Tunnel status.";
        }
        leaf error-type {
          type dgntl-error-type;
          config false;
          status deprecated;
          description
            "Test operation status.";
        }
        container trace-result-details {
          config false;
          status deprecated;
          description
            "List of ping results of all packets in a test.";
          list trace-result-detail {
            key "hop-index";
            config false;
            status deprecated;
            description
              "Statistics of ping result of a single packet in a test.";
            leaf hop-index {
              type uint32;
              config false;
              status deprecated;
              description
                "Serial number of a hop in the test path. For a ping-type test such as the ping test or LSP ping test, there is only one hop in the test path, so the value is 1. For a trace-type test such as the trace test or LSP trace test, the value indicates the exact serial number of a hop in the test path.";
            }
            leaf ds-ip-addr {
              type inet:ipv4-address-no-zone;
              config false;
              status deprecated;
              description
                "Destination address of the related hop in a test.";
            }
            leaf down-stream-ip-addr {
              type inet:ipv4-address-no-zone;
              config false;
              status deprecated;
              description
                "Downstream address of the related hop in a test.";
            }
            leaf rtt {
              type uint32;
              config false;
              status deprecated;
              description
                "RTT of test packets.";
            }
            leaf type {
              type transmit-type;
              config false;
              status deprecated;
              description
                "Node type.";
            }
            leaf ttl {
              type uint8 {
                range "1..255";
              }
              config false;
              status deprecated;
              description
                "TTL of received response packets.";
            }
            leaf ds-label {
              type uint32;
              config false;
              status deprecated;
              description
                "Downstream label.";
            }
            leaf ret-code {
              type uint32;
              config false;
              status deprecated;
              description
                "Return code.";
            }
            container downstreams {
              config false;
              status deprecated;
              description
                "List of downstream informations.";
              list downstream {
                key "ds-label";
                config false;
                status deprecated;
                description
                  "Statistics of downstream information.";
                leaf ds-label {
                  type uint32;
                  config false;
                  status deprecated;
                  description
                    "Downstream labels.";
                }
              }
            }
            leaf is-delete {
              ext:support-filter "true";
              type boolean;
              config false;
              status deprecated;
              description
                "Enable/disable the function of deleting test results.";
            }
          }
        }
        container hops {
          config false;
          description
            "List of hop results.";
          list hop {
            key "hop-index";
            config false;
            description
              "Statistics of hop result.";
            leaf hop-index {
              type uint32;
              config false;
              description
                "The index of the hop.";
            }
            leaf replier {
              type inet:ipv4-address-no-zone;
              config false;
              description
                "Reply address of the related hop in a test.";
            }
            leaf rtt {
              type uint32;
              config false;
              description
                "RTT of test packets, expressed in milliseconds.";
            }
            leaf type {
              type transmit-type;
              config false;
              description
                "Node type.";
            }
            leaf return-code {
              type uint32;
              config false;
              description
                "Return code.";
            }
            leaf result-type {
              type probe-result-type;
              config false;
              description
                "Result of packet sending, which is either Success or Timeout.";
            }
            leaf is-delete {
              ext:support-filter "true";
              type boolean;
              config false;
              description
                "Enable/disable the function of deleting test results.";
            }
            container downstreams {
              config false;
              description
                "List of downstream information tables.";
              list downstream {
                key "ds-index";
                config false;
                description
                  "Statistics of downstream information table.";
                leaf ds-index {
                  type uint32;
                  config false;
                  description
                    "The index of the ds.";
                }
                leaf ds-address {
                  type inet:ipv4-address-no-zone;
                  config false;
                  description
                    "Downstream address of the related hop in a test.";
                }
                container ds-label-lists {
                  config false;
                  description
                    "List of downstream label information tables.";
                  list ds-label-list {
                    key "label-index";
                    config false;
                    description
                      "Statistics of downstream label information table.";
                    leaf label-index {
                      type uint32;
                      config false;
                      description
                        "The index of the ds label.";
                    }
                    leaf ds-label {
                      type uint32;
                      config false;
                      description
                        "Downstream labels.";
                    }
                  }
                }
              }
            }
          }
        }
      }
    }
  }
  rpc lsp-start-ping {
    status deprecated;
    description
      "Start lsp ping.";
    ext:node-ref "/diagnostic-tools:diagnostic-tools/diagnostic-tools:ipv4/diagnostic-tools:ping-results";
    input {
      choice lsp-protocol {
        description
          "Lsp protocol.";
        case srte {
          description
            "Lsp protocol srte.";
          container srte-test {
            description
              "Lsp protocol srte.";
            leaf test-name {
              type string {
                length "1..32";
              }
              mandatory true;
              description
              "Test name.";
            }
            leaf tunnel-name {
              type string {
                length "1..33";
              }
              mandatory true;
              description
                "Tunnel name.";
            }
          }
        }
        case srbe {
          description
            "Lsp protocol srbe.";
          container srbe-test {
            description
              "Lsp protocol srbe.";
            leaf test-name {
              type string {
                length "1..32";
              }
              mandatory true;
              description
              "Test name.";
            }
            leaf dest-ip-addr {
              type pub-type:host-name;
              mandatory true;
              description
                "Destination address of the string type. You can click this node to set different types of addresses and deploy the configurations together with the configuration of the destination address type node. If the destination address type is set to IPv4, this parameter is set to IPv4. If the destination address type is set to IPv6, this parameter is set to IPv6.";
            }
            leaf mask-len {
              type uint8 {
                range "0..32";
              }
              mandatory true;
              description
                "Mask length.";
            }
            leaf version {
              type sr-be-version;
              mandatory true;
              description
                "SR-TE Version: 'DRAFT' indicates the RSVP IPv4 Fec in SRTE packet.";
            }
          }
        }             
      }
    }
  }
  rpc start-lsp-ping {
    description
      "Start lsp ping.";
    ext:node-ref "/diagnostic-tools:diagnostic-tools/diagnostic-tools:ipv4/diagnostic-tools:ping-results";
    input {
      leaf test-name {
        type string {
          length "1..32";
        }
        mandatory true;
        description
          "Test name.";
      }
      choice lsp-protocol {
        description
          "Lsp protocol.";
        case te {
          description
            "Lsp protocol te.";
            leaf te-tunnel-name {
              type string {
                length "1..33";
              }
              mandatory true;
              description
                "Tunnel name.";
            }
            leaf te-lsp-path {
              type lsp-path;
              default "working-path";
              description
                "Lsp Path.";
            }
            leaf te-compatible-mode {
              type boolean;
              default "false";
              description
                "Compatible mode.";
            }
            leaf te-reply-mode {
              type reply-mode-te;
              default "udp";
              description
                "Reply Mode.";
            }
          }
        case srte {
          description
            "Lsp protocol srte.";
            leaf srte-tunnel-name {
              type string {
                length "1..33";
              }
              mandatory true;
              description
                "Tunnel name.";
            }
            leaf srte-remote-address {
              type inet:ipv4-address-no-zone;
              description
                "Remote Address.";
            }
            leaf srte-lsp-path {
              type lsp-path;
              default "working-path";
              description
                "Lsp Path.";
            }
            leaf srte-reply-mode {
              type reply-mode-srte;
              default "udp";
              description
                "Reply Mode.";
            }
          }
        case auto-srte {
          description
            "Lsp protocol auto-srte.";
            leaf auto-srte-tunnel-name {
              type string {
                length "1..33";
              }
              mandatory true;
              description
                "Tunnel name.";
            }
            leaf auto-srte-remote-address {
              type inet:ipv4-address-no-zone;
              description
                "Remote Address.";
            }
            leaf auto-srte-lsp-path {
              type lsp-path;
              default "working-path";
              description
                "Lsp Path.";
            }
            leaf auto-srte-reply-mode {
              type reply-mode-te;
              default "udp";
              description
                "Reply Mode.";
            }
          }
        case srbe {
          description
            "Lsp protocol srbe.";
            leaf srbe-dest-address {
              type pub-type:host-name;
              mandatory true;
              description
                "Destination address.";
            }
            leaf srbe-mask-len {
              type uint8 {
                range "0..32";
              }
              mandatory true;
              description
                "Mask length.";
            }
            leaf srbe-remote-address {
              type inet:ipv4-address-no-zone;
              description
                "Remote Address.";
            }
            leaf srbe-remote-fec {
              type lsp-remote-fec-type;
              description
                "Remote FEC type.";
            }
            leaf srbe-remote-fec-address {
              type inet:ipv4-address-no-zone;
              description
                "Remote FEC IPv4 address.";
            }
            leaf srbe-remote-mask-len {
              type uint8 {
                range "0..32";
              }
              description
                "Remote FEC mask length.";
            }
            leaf srbe-by-pass {
              type boolean;
              default "false";
              description
                "By pass flag.";
            }
            leaf srbe-reply-mode {
              type reply-mode-srbe;
              default "udp";
              description
                "Reply Mode.";
            }
            leaf flex-algo-id {
              type uint8 {
                range "128..255";
              }
              description
                "Flexible algorithm ID.";
            }
          }
      }
      leaf source-address {
        type inet:ipv4-address-no-zone;
        description
          "The source address of the targeted session.";
      }
      leaf next-hop {
        type inet:ipv4-address-no-zone;
        description
          "Next hop address.";
      }
      leaf count {
        type uint32 {
          range "1..4294967295";
        }
        default "5";
        description
          "Number of sent test packets.";
      }
      leaf exp {
        type uint32 {
          range "0..7";
        }
        default "0";
        description
          "EXP value in the label field of MPLS packets. The EXP value is used to distinguish the service types of MPLS packets.";
      }
      leaf ttl {
        type uint8 {
          range "1..255";
        }
        default "255";
        description
          "TTL value.";
      }
      leaf interval {
        type uint32 {
          range "1..10000";
        }
        units "ms";
        default "2000";
        description
          "Interval for sending test packets.";
      }
      leaf packet-size {
        type uint32 {
          range "65..9600";
        }
        default "100";
        description
          "Number of bytes in a sent test packet.";
      }
      leaf timeout {
        type uint32 {
          range "0..65535";
        }
        units "ms";
        default "2000";
        description
          "Time to wait for a response packet after a test packet is sent. If no response packet is received within the timeout period, the system considers that the test packet times out.";
      }
      leaf fragment {
        type boolean;
        default "false";
        description
          "Set the Fragment flag in packet.";
      }
    }
  }
  rpc lsp-stop-ping {
    description
      "Stop lsp ping.";
    ext:node-ref "/diagnostic-tools:diagnostic-tools/diagnostic-tools:ipv4/diagnostic-tools:ping-results";
    input {
      leaf test-name {
        type leafref {
          path "/diagnostic-tools:diagnostic-tools/diagnostic-tools:lsp/diagnostic-tools:ping-results/diagnostic-tools:ping-result/diagnostic-tools:test-name";
        }
        mandatory true;
        description
          "Test name.";
      }
    }
  }

  rpc lsp-delete-ping {
    description
      "Delete lsp ping.";
    ext:node-ref "/diagnostic-tools:diagnostic-tools/diagnostic-tools:ipv4/diagnostic-tools:ping-results";
    input {
      leaf test-name {
        type leafref {
          path "/diagnostic-tools:diagnostic-tools/diagnostic-tools:lsp/diagnostic-tools:ping-results/diagnostic-tools:ping-result/diagnostic-tools:test-name";
        }
        mandatory true;
        description
          "Test name.";
      }
    }
  }

  rpc lsp-start-trace {
    status deprecated;
    description
      "Start lsp trace.";
    ext:node-ref "/diagnostic-tools:diagnostic-tools/diagnostic-tools:lsp/diagnostic-tools:trace-results";
    input {
      choice lsp-protocol {
        description
          "Lsp protocol.";
        case srte {
          description
            "Lsp protocol srte.";
          container srte-test {
            description
              "Lsp protocol srte.";
            leaf test-name {
              type string {
                length "1..255";
              }
              mandatory true;
              description
                "Test name.";
            }
            leaf tunnel-name {
              type string {
                length "1..33";
              }
              mandatory true;
              description
                "Tunnel name.";
            }
          }
        }
        case srbe {
          description
            "Lsp protocol srbe.";
          container srbe-test {
            description
              "Lsp protocol srbe.";
            leaf test-name {
              type string {
                length "1..255";
              }
              mandatory true;
              description
                "Test name.";
            }
            leaf dest-ip-addr {
              type pub-type:host-name;
              mandatory true;
              description
                "Destination address of the string type. You can click this node to set different types of addresses and deploy the configurations together with the configuration of the destination address type node. If the destination address type is set to IPv4, this parameter is set to IPv4. If the destination address type is set to IPv6, this parameter is set to IPv6.";
            }
            leaf mask-len {
              type uint8 {
                range "0..32";
              }
              mandatory true;
              description
                "Mask length.";
            }
            leaf version {
              type sr-be-version;
              mandatory true;
              description
                "SR-TE Version: 'DRAFT' indicates the RSVP IPv4 Fec in SRTE packet.";
            }
          }
        }
      }
    }
  }
  
  rpc start-lsp-trace {
    description
      "Start lsp trace.";
    ext:node-ref "/diagnostic-tools:diagnostic-tools/diagnostic-tools:lsp/diagnostic-tools:trace-results";
    input {
      leaf test-name {
        type string {
          length "1..32";
        }
        mandatory true;
        description
          "Test name.";
      }
      choice lsp-protocol {
        description
          "Lsp protocol.";
        case ldp {
          description
            "Lsp protocol ldp.";
          leaf ldp-dest-address {
            type pub-type:host-name;
            mandatory true;
            description
              "Destination address.";
          }
          leaf ldp-mask-len {
            type uint8 {
              range "0..32";
            }
            mandatory true;
            description
              "Mask length.";
          }
          leaf ldp-loopback-address {
            type inet:ipv4-address-no-zone;
            description
              "Destination address of IP header in MPLS message. Its prefixion is 127.0.0.0/8.";
          }
          leaf ldp-reply-mode {
            type reply-mode-ip;
            default "udp";
            description
              "Reply Mode.";
          }
          leaf ldp-ddmap {
            type boolean;
            default "false";
            description
              "Ddmap TLV enable.";
          }
        }
        case te {
          description
            "Lsp protocol te.";
          leaf te-tunnel-name {
            type string {
              length "1..33";
            }
            mandatory true;
            description
              "Tunnel name.";
          }
          leaf te-lsp-path {
            type lsp-path;
            description
              "Lsp Path.";
          }
          leaf te-compatible-mode {
            type boolean;
            description
              "Compatible mode.";
          }
          leaf te-reply-mode {
            type reply-mode-te;
            default "udp";
            description
              "Reply Mode.";
          }
        }
        case srte {
          description
            "Lsp protocol srte.";
          leaf srte-tunnel-name {
            type string {
              length "1..33";
            }
            mandatory true;
            description
              "Tunnel name.";
          }
          leaf srte-lsp-path {
            type lsp-path;
            description
              "Lsp Path.";
          }
          leaf srte-reply-mode {
            type reply-mode-srte;
            default "udp";
            description
              "Reply Mode.";
          }
          leaf srte-version {
            type sr-version;
            description
              "SR-TE Version: 'DRAFT2' Draft-ietf-MPLS-spring-lsp-ping-02; 'RFC8287' RFC 8287.";
          }
        }
        case auto-srte {
          description
            "Lsp protocol auto-srte.";
          leaf auto-srte-tunnel-name {
            type string {
              length "1..33";
            }
            mandatory true;
            description
              "Tunnel name.";
          }
          leaf auto-srte-lsp-path {
            type lsp-path;
            description
              "Lsp Path.";
          }
          leaf auto-srte-reply-mode {
            type reply-mode-te;
            default "udp";
            description
              "Reply Mode.";
          }
        }
        case srbe {
          description
            "Lsp protocol srbe.";
          leaf srbe-dest-address {
            type pub-type:host-name;
            mandatory true;
            description
              "Destination address.";
          }
          leaf srbe-mask-len {
            type uint8 {
              range "0..32";
            }
            mandatory true;
            description
              "Mask length.";
          }
          leaf srbe-remote-address {
            type inet:ipv4-address-no-zone;
            description
              "Remote Address.";
          }
          leaf srbe-remote-fec {
            type lsptrace-remote-fec-type;
            description
              "Remote FEC type.";
          }
          leaf srbe-remote-fec-address {
            type inet:ipv4-address-no-zone;
            description
              "Remote FEC IPv4 address.";
          }
          leaf srbe-remote-mask-len {
            type uint8 {
              range "0..32";
            }
            description
              "Remote FEC mask length.";
          }
          leaf srbe-by-pass {
            type boolean;
            description
              "By pass flag.";
          }
          leaf flex-algo-id {
            type uint8 {
              range "128..255";
            }
            description
              "Flexible algorithm ID.";
          }
        }
      }
      leaf source-address {
        type inet:ipv4-address-no-zone;
        description
          "The source address of the targeted session.";
      }
      leaf next-hop {
        type inet:ipv4-address-no-zone;
        description
          "Next hop address.";
      }
      leaf exp {
        type uint32 {
          range "0..7";
        }
        default "0";
        description
          "EXP value in the label field of MPLS packets. The EXP value is used to distinguish the service types of MPLS packets.";
      }
      leaf ttl {
        type uint8 {
          range "1..255";
        }
        description
          "TTL value.";
      }
      leaf packet-size {
        type uint32 {
          range "100..9600";
        }
        default "100";
        description
          "Number of bytes in a sent test packet.";
      }
      leaf timeout {
        type uint32 {
          range "0..65535";
        }
        units "ms";
        default "2000";
        description
          "Time to wait for a response packet after a test packet is sent. If no response packet is received within the timeout period, the system considers that the test packet times out.";
      }
      leaf fragment {
        type boolean;
        default "false";
        description
          "Set the Fragment flag in packet.";
      }
    }
  }

  rpc lsp-stop-trace {
    description
      "Stop lsp trace.";
    ext:node-ref "/diagnostic-tools:diagnostic-tools/diagnostic-tools:lsp/diagnostic-tools:trace-results";
    input {
      leaf test-name {
        type leafref {
          path "/diagnostic-tools:diagnostic-tools/diagnostic-tools:lsp/diagnostic-tools:trace-results/diagnostic-tools:trace-result/diagnostic-tools:test-name";
        }
        mandatory true;
        description
          "Test name.";
      }
    }
  }

  rpc lsp-delete-trace {
    description
      "Delete lsp trace.";
    ext:node-ref "/diagnostic-tools:diagnostic-tools/diagnostic-tools:lsp/diagnostic-tools:trace-results";
    input {
      leaf test-name {
        type leafref {
          path "/diagnostic-tools:diagnostic-tools/diagnostic-tools:lsp/diagnostic-tools:trace-results/diagnostic-tools:trace-result/diagnostic-tools:test-name";
        }
        mandatory true;
        description
          "Test name.";
      }
    }
  }

  augment "/diagnostic-tools:diagnostic-tools" {
    description
      "List of LSP ping and trace tests.";
    container lsp {
      config false;
      description
        "Statistics of LSP ping and trace tests.";
      uses diagnostic-tools:lsp-ping-trace-result-type;
    }
  }
}
