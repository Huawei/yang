/*
Copyright (C) 2020 Huawei Technologies Co., Ltd. All rights reserved.
*/
module huawei-rgm-deviations-NE9000 {
  yang-version 1;
  namespace "urn:huawei:yang:huawei-rgm-deviations-NE9000";
  prefix rgm-devs-NE9000;

  import huawei-rgm {
    prefix rgm;
  }
  import huawei-ifm {
    prefix ifm;
  }
  import huawei-ip {
    prefix ip;
  }

  organization
    "Huawei Technologies Co., Ltd.";
  contact
    "Huawei Industrial Base
     Bantian, Longgang
     Shenzhen 518129
     People's Republic of China
     Website: http://www.huawei.com
     Email: support@huawei.com";
  description
    "IPv4 Direct Route Association.";

  revision 2020-01-20 {
    description
      "Init revision.";
    reference "Huawei private.";
  }

  deviation "/ifm:ifm/ifm:interfaces/ifm:interface/ip:ipv4/rgm:rgm/rgm:track-rtmtg" {
    deviate not-supported;
  }
}
