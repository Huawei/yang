/*
Copyright (C) 2019 Huawei Technologies Co., Ltd. All rights reserved.
*/
module huawei-patch-deviations-NE9000 {
  namespace "urn:huawei:yang:huawei-patch-deviations-NE9000";
  prefix patch-devs-NE9000;

  import huawei-patch {
    prefix patch;
  }

  organization
    "Huawei Technologies Co., Ltd.";
  contact
    "Huawei Industrial Base
     Bantian, Longgang
     Shenzhen 518129
     People's Republic of China
     Website: http://www.huawei.com
     Email: support@huawei.com";
  description
    "Patch deviations.";

  revision 2019-12-10 {
    description
      "Initial revision.";
    reference "Huawei private.";
  }

  deviation "/patch:patch/patch:next-startup-patchs" {
    deviate not-supported;
  }
  deviation "/patch:patch/patch:operation-schedules/patch:operation-schedule/patch:name" {
    deviate not-supported;
  }
  deviation "/patch:patch/patch:download-package-schedule" {
    deviate not-supported;
  }
  deviation "/patch:patch/patch:download-package-load-path" {
    deviate not-supported;
  }
  deviation "/patch:download-patch-file" {
    deviate not-supported;
  }
}
