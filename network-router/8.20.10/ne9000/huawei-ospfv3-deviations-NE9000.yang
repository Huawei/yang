/*
Copyright (C) 2019 Huawei Technologies Co., Ltd. All rights reserved.
*/
module huawei-ospfv3-deviations-NE9000 {
  namespace "urn:huawei:yang:huawei-ospfv3-deviations-NE9000";
  prefix ospfv3-devs-NE9000;

  import huawei-ospfv3 {
    prefix ospfv3;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "OSPFv3 management.";

  revision 2019-04-04 {
    description
      "Initial revision.";
    reference "Huawei private.";
  }

  deviation "/ni:network-instance/ni:instances/ni:instance/ospfv3:ospfv3/ospfv3:sites/ospfv3:site/ospfv3:spf-control/ospfv3:max-load-balancing" {
    deviate replace {
      type uint32 {
        range "1..64";
      }
      default "64";
    }
  }
  deviation "/ospfv3:ospfv3/ospfv3:advertise-max-cost" {
    deviate not-supported;
  }
  deviation "/ni:network-instance/ni:instances/ni:instance/ospfv3:ospfv3/ospfv3:sites/ospfv3:site/ospfv3:cost-bindings" {
    deviate not-supported;
  }
  deviation "/ni:network-instance/ni:instances/ni:instance/ospfv3:ospfv3/ospfv3:sites/ospfv3:site/ospfv3:bgp-ls" {
    deviate not-supported;
  }
}
