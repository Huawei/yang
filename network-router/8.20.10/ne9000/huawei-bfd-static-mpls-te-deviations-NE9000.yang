/*
Copyright (C) 2019 Huawei Technologies Co., Ltd. All rights reserved.
*/
module huawei-bfd-static-mpls-te-deviations-NE9000 {
  yang-version 1;
  namespace "urn:huawei:yang:huawei-bfd-static-mpls-te-deviations-NE9000";
  prefix bfd-mpls-te-devs-NE9000;

  import huawei-bfd {
    prefix bfd;
  }
  import huawei-bfd-static-mpls-te {
    prefix bfd-static-mpls-te;
  }
  import huawei-devm {
    prefix devm;
  }

  organization
    "Huawei Technologies Co., Ltd.";
  contact
    "Huawei Industrial Base
     Bantian, Longgang
     Shenzhen 518129
     People's Republic of China
     Website: http://www.huawei.com
     Email: support@huawei.com";
  description
    "Bidirectional Forwarding Detection (BFD) is a detection mechanism used uniformly on the entire network. BFD is used to rapidly detect and monitor the connectivity of links or IP routes on a network.";

  revision 2019-04-23 {
    description
      "Initial revision.";
    reference "Huawei private.";
  }

  deviation "/bfd:bfd/bfd:sessions/bfd:session/bfd:session-type/bfd:static/bfd:static-session-link-type/bfd-static-mpls-te:te-tunnel/bfd-static-mpls-te:select-board-slot-static-te-tunnel" {
    deviate replace {
      type leafref {
        path "/devm:devm/devm:lpu-boards/devm:lpu-board/devm:position";
      }
    }
  }
  deviation "/bfd:bfd/bfd:sessions/bfd:session/bfd-static-mpls-te:mpls-te-groups/bfd-static-mpls-te:mpls-te-group/bfd-static-mpls-te:sub-select-slot-id" {
    deviate replace {
      type leafref {
        path "/devm:devm/devm:lpu-boards/devm:lpu-board/devm:position";
      }
    }
  }
}
