/*
Copyright (C) 2019 Huawei Technologies Co., Ltd. All rights reserved.
*/
module huawei-nd-deviations-NE9000 {
  namespace "urn:huawei:yang:huawei-nd-deviations-NE9000";
  prefix nd-devs-NE9000;

  import huawei-nd {
    prefix nd;
  }

  organization
    "Huawei Technologies Co., Ltd.";
  contact
    "Huawei Industrial Base
     Bantian, Longgang
     Shenzhen 518129
     People's Republic of China
     Website: http://www.huawei.com
     Email: support@huawei.com";
  description
    "ND management.";

  revision 2019-04-24 {
    description
      "Initial revision.";
    reference "Huawei private.";
  }

  deviation "/nd:nd/nd:ipv6-neighbors/nd:ipv6-neighbor/nd:nickname" {
    deviate not-supported;
  }
  deviation "/nd:nd/nd:ipv6-neighbors/nd:ipv6-neighbor/nd:bd-id" {
    deviate replace {
      type uint32 {
        range "1..32768";
      }
    }
  }
}
