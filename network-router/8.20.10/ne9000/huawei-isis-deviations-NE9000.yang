/*
Copyright (C) 2019 Huawei Technologies Co., Ltd. All rights reserved.
*/
module huawei-isis-deviations-NE9000 {
  namespace "urn:huawei:yang:huawei-isis-deviations-NE9000";
  prefix isis-devs-NE9000;

  import huawei-isis {
    prefix isis;
  }
  import huawei-network-instance {
    prefix ni;
  }
  import huawei-mpls {
    prefix mpls;
  }
  import huawei-mpls-ldp {
    prefix mpls-ldp;
  }
  import huawei-l3vpn {
    prefix l3vpn;
  }
  import huawei-routing {
    prefix rt;
  }

  organization
    "Huawei Technologies Co., Ltd.";
  contact
    "Huawei Industrial Base
     Bantian, Longgang
     Shenzhen 518129
     People's Republic of China
     Website: http://www.huawei.com
     Email: support@huawei.com";
  description
    "IS-IS management.";

  revision 2019-04-04 {
    description
      "Initial revision.";
    reference "Huawei private.";
  }

  deviation "/ni:network-instance/ni:instances/ni:instance/isis:isis/isis:sites/isis:site/isis:extern-ability/isis:virtual-access" {
    deviate not-supported;
  }
  deviation "/ni:network-instance/ni:instances/ni:instance/isis:isis/isis:sites/isis:site/isis:extern-ability/isis:virtual-cluster" {
    deviate not-supported;
  }
  deviation "/ni:network-instance/ni:instances/ni:instance/isis:isis/isis:sites/isis:site/isis:afs/isis:af/isis:max-load-balancing" {
    deviate replace {
      type uint32 {
        range "1..64";
      }
      default "64";
    }
  }
  deviation "/ni:network-instance/ni:instances/ni:instance/isis:isis/isis:sites/isis:site/isis:afs/isis:af/isis:topologys/isis:topology/isis:max-load-balancing" {
    deviate replace {
      type uint32 {
        range "1..64";
      }
      default "64";
    }
  }
  deviation "/isis:isis/isis:global-stat" {
    deviate not-supported;
  }
  deviation "/ni:network-instance/ni:instances/ni:instance/isis:isis/isis:sites/isis:site/isis:afs/isis:af/isis:mpls-ldp-global/isis:auto-flag" {
    deviate add {
      must "../auto-flag='false' or (../../../../../../../ni:name='_public_' and /mpls:mpls/mpls-ldp:ldp/mpls-ldp:enable='true')";
    }
  }
  deviation "/ni:network-instance/ni:instances/ni:instance/l3vpn:afs/l3vpn:af/isis:isis-import-rts/isis:isis-import-rt/isis:src-vrf" {
    deviate add {
      must "(../../../l3vpn:type='ipv4-unicast' and /ni:network-instance/ni:instances/ni:instance[ni:name=current()]/l3vpn:afs/l3vpn:af[l3vpn:type='ipv4-unicast']) or (../../../l3vpn:type='ipv6-unicast' and /ni:network-instance/ni:instances/ni:instance[ni:name=current()]/l3vpn:afs/l3vpn:af[l3vpn:type='ipv6-unicast'])";
    }
  }
  deviation "/ni:network-instance/ni:instances/ni:instance/isis:isis/isis:sites/isis:site/isis:circuits/isis:circuit/isis:afs/isis:af/isis:topologys/isis:topology" {
    deviate delete {
      must "((../../isis:type='afipv4') and (../../../../../../../../../l3vpn:afs/l3vpn:af[l3vpn:type='ipv4-unicast']/rt:routing/rt:direct-routing/rt:interfaces/rt:interface[rt:name=current()/../../../../isis:name]/rt:binding-topologys/rt:binding-topology[rt:topology-name=current()/../../../../../../isis:afs/isis:af[isis:type=current()/../../isis:type]/isis:topologys/isis:topology[isis:mt-id=current()/isis:mt-id]/isis:topo-name])) or ((../../isis:type='afipv6') and (../../../../../../../../../l3vpn:afs/l3vpn:af[l3vpn:type='ipv6-unicast']/rt:routing/rt:direct-routing/rt:interfaces/rt:interface[rt:name=current()/../../../../isis:name]/rt:binding-topologys/rt:binding-topology[rt:topology-name=current()/../../../../../../isis:afs/isis:af[isis:type=current()/../../isis:type]/isis:topologys/isis:topology[isis:mt-id=current()/isis:mt-id]/isis:topo-name]))";
    }
  }
}
