/*
Copyright (C) 2019 Huawei Technologies Co., Ltd. All rights reserved.
*/
module huawei-mac-deviations-NE9000 {
  yang-version 1;
  namespace "urn:huawei:yang:huawei-mac-deviations-NE9000";
  prefix mac-devs-NE9000;

  import huawei-mac {
    prefix mac;
  }
  import huawei-vlan {
    prefix vlan;
  }
  import huawei-l2vpn {
    prefix l2vpn;
  }
  import huawei-ifm {
    prefix ifm;
  }
  import huawei-ethernet {
    prefix ethernet;
  }

  organization
    "Huawei Technologies Co., Ltd.";
  contact
    "Huawei Industrial Base
     Bantian, Longgang
     Shenzhen 518129
     People's Republic of China
     Website: http://www.huawei.com
     Email: support@huawei.com";
  description
    "MAC address forwarding.";

  revision 2019-04-23 {
    description
      "Initial revision.";
    reference "Huawei private.";
  }

  typedef mac-type-deviations {
    type enumeration {
      enum dynamic {
        value 2;
        description
          "Dynamic type.";
      }
      enum dynamic-black-hole {
        value 15;
        description
          "Dynamic blackhole MAC.";
      }
    }
    description
      "MAC type.";
  }

  deviation "/mac:mac/mac:bd-dynamic-macs/mac:bd-dynamic-mac/mac:type" {
    deviate replace {
      type mac-devs-NE9000:mac-type-deviations;
    }
  }
  deviation "/vlan:vlan/vlan:vlans/vlan:vlan/mac:mac-limit/mac:alarm" {
    deviate not-supported;
  }
  deviation "/l2vpn:l2vpn/l2vpn:instances/l2vpn:instance/l2vpn:vpls/mac:mac/mac:mac-limit/mac:alarm" {
    deviate not-supported;
  }
  deviation "/mac:mac/mac:bd-mac-total-numbers" {
    deviate not-supported;
  }
  deviation "/mac:mac/mac:mac-statistics" {
    deviate not-supported;
  }
  deviation "/mac:mac/mac:bd-dynamic-macs/mac:bd-dynamic-mac/mac:learned-period" {
    deviate not-supported;
  }
  deviation "/mac:mac/mac:bd-dynamic-macs/mac:bd-dynamic-mac/mac:vsi-name" {
    deviate not-supported;
  }
  deviation "/l2vpn:l2vpn/l2vpn:instances/l2vpn:instance/l2vpn:vpls/mac:mac/mac:mac-addresss/mac:unqualifys/mac:unqualify/mac:mac-type/mac:static/mac:out-bound-type/mac:ac/mac:ce-any" {
    deviate not-supported;
  }
  deviation "/ifm:ifm/ifm:interfaces/ifm:interface/ethernet:ethernet/ethernet:main-interface/mac:mac-limit/mac:limit-type/mac:limit-parameter/mac:maximum" {
    deviate add {
      must '(../../ethernet:l2-attribute) or (/l2vpn:l2vpn/l2vpn:instances/l2vpn:instance/l2vpn:vpls/l2vpn:acs/l2vpn:ac[l2vpn:interface-name=current()/../../../../ifm:name])';
    }
  }
  deviation "/ifm:ifm/ifm:interfaces/ifm:interface/ethernet:ethernet/ethernet:main-interface/mac:mac-limit/mac:limit-type/mac:limit-rule-ref/mac:rule-name" {
    deviate add {
      must '../../ethernet:l2-attribute';
    }
  }
}
