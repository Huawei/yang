/*
Copyright (C) 2019 Huawei Technologies Co., Ltd. All rights reserved.
*/
module huawei-ifit-statistics-deviations-NE9000 {
  namespace "urn:huawei:yang:huawei-ifit-statistics-deviations-NE9000";
  prefix ifit-statistics-devs-NE9000;

  import huawei-ifit-statistics {
    prefix ifit-statistics;
  }

  import huawei-ifit {
    prefix ifit;
  }

  organization
    "Huawei Technologies Co., Ltd.";

  contact
    "Huawei Industrial Base
     Bantian, Longgang
     Shenzhen 518129
     People's Republic of China
     Website: http://www.huawei.com
     Email: support@huawei.com";

  description
    "This module defines deviation statements for huawei-ifit-statistics module.";

  revision 2019-11-06 {
    description
      "Initial revision.";
    reference
      "Huawei private.";
  }

  deviation "/ifit:ifit/ifit-statistics:flow-statistics/ifit-statistics:flow-statistic/ifit-statistics:tunnel-if-index" {
    deviate not-supported;
  }
  deviation "/ifit:ifit/ifit-statistics:flow-statistics/ifit-statistics:flow-statistic/ifit-statistics:cfg-id" {
    deviate not-supported;
  }
  deviation "/ifit:ifit/ifit-statistics:flow-statistics/ifit-statistics:flow-statistic/ifit-statistics:measure-mode" {
    deviate not-supported;
  }
  deviation "/ifit:ifit/ifit-statistics:flow-peer-ip-statistics/ifit-statistics:flow-peer-ip-statistic/ifit-statistics:evpn-name" {
    deviate not-supported;
  }
  deviation "/ifit:ifit/ifit-statistics:flow-peer-ip-statistics/ifit-statistics:flow-peer-ip-statistic/ifit-statistics:ttl" {
    deviate not-supported;
  }
  deviation "/ifit:ifit/ifit-statistics:flow-locator-statistics/ifit-statistics:flow-locator-statistic/ifit-statistics:evpn-name" {
    deviate not-supported;
  }
  deviation "/ifit:ifit/ifit-statistics:flow-locator-statistics/ifit-statistics:flow-locator-statistic/ifit-statistics:ttl" {
    deviate not-supported;
  }
  deviation "/ifit:ifit/ifit-statistics:flow-hop-statistics/ifit-statistics:flow-hop-statistic/ifit-statistics:tunnel-if-index" {
    deviate not-supported;
  }
  deviation "/ifit:ifit/ifit-statistics:flow-hop-statistics/ifit-statistics:flow-hop-statistic/ifit-statistics:cfg-id" {
    deviate not-supported;
  }
  deviation "/ifit:ifit/ifit-statistics:flow-hop-statistics/ifit-statistics:flow-hop-statistic/ifit-statistics:measure-mode" {
    deviate not-supported;
  }
  deviation "/ifit:ifit/ifit-statistics:flow-hop-statistics/ifit-statistics:flow-hop-statistic/ifit-statistics:maximum-delay" {
    deviate not-supported;
  }
  deviation "/ifit:ifit/ifit-statistics:flow-hop-statistics/ifit-statistics:flow-hop-statistic/ifit-statistics:minimum-delay" {
    deviate not-supported;
  }
  deviation "/ifit:ifit/ifit-statistics:flow-hop-statistics/ifit-statistics:flow-hop-statistic/ifit-statistics:total-delay" {
    deviate not-supported;
  }
  deviation "/ifit:ifit/ifit-statistics:flow-hop-statistics/ifit-statistics:flow-hop-statistic/ifit-statistics:total-count" {
    deviate not-supported;
  }
  deviation "/ifit:ifit/ifit-statistics:flow-vpws-statistics" {
    deviate not-supported;
  }

}
