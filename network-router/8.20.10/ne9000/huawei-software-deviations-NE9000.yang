/*
Copyright (C) 2020 Huawei Technologies Co., Ltd. All rights reserved.
*/
module huawei-software-deviations-NE9000 {
  namespace "urn:huawei:yang:huawei-software-deviations-NE9000";
  prefix software-devs-NE9000;

  import huawei-software {
    prefix software;
  }

  organization
    "Huawei Technologies Co., Ltd.";
  contact
    "Huawei Industrial Base
     Bantian, Longgang
     Shenzhen 518129
     People's Republic of China
     Website: http://www.huawei.com
     Email: support@huawei.com";
  description
    "Specify software package upgrade management.";

  revision 2020-01-02 {
    description
      "Initial revision.";
    reference "Huawei private.";
  }

  deviation "/software:software/software:global" {
    deviate not-supported;
  }
  deviation "/software:software/software:packages/software:package/software:package-type" {
    deviate not-supported;
  }
  deviation "/software:software/software:checkpoint-infos" {
    deviate not-supported;
  }
  deviation "/software:install-feature-software" {
    deviate not-supported;
  }
  deviation "/software:uninstall-feature-software" {
    deviate not-supported;
  }
  deviation "/software:upgrade-feature-software" {
    deviate not-supported;
  }
  deviation "/software:startup-feature-software" {
    deviate not-supported;
  }
  deviation "/software:create-startup-checkpoint" {
    deviate not-supported;
  }
  deviation "/software:delete-startup-checkpoint" {
    deviate not-supported;
  }
  deviation "/software:check-startup-checkpoint" {
    deviate not-supported;
  }
  deviation "/software:restore-startup-checkpoint" {
    deviate not-supported;
  }
  deviation "/software:refresh-startup-secure-version-configuration" {
    deviate not-supported;
  }
}
