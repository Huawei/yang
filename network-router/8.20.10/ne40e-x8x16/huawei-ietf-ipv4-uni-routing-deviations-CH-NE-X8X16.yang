/*
Copyright (C) 2021 Huawei Technologies Co., Ltd. All rights reserved.
*/
module huawei-ietf-ipv4-uni-routing-deviations-CH-NE-X8X16 {
  yang-version 1.1;
  namespace "urn:huawei:yang:huawei-ietf-ipv4-uni-routing-deviations-CH-NE-X8X16";
  prefix v4ur-devs-CH-NE-X8X16;

  import ietf-ipv4-unicast-routing {
    prefix v4ur;
  }
  import ietf-routing {
    prefix rt;
  }

  organization
    "Huawei Technologies Co., Ltd.";
  contact
    "Huawei Industrial Base
     Bantian, Longgang
     Shenzhen 518129
     People's Republic of China
     Website: http://www.huawei.com
     Email: support@huawei.com";
  description
    "Deviations for ietf-network model.";

  revision 2021-01-15 {
    description
      "Initial revision.";
    reference "Huawei private.";
  }

  deviation "/rt:routing/rt:control-plane-protocols/rt:control-plane-protocol/rt:static-routes/v4ur:ipv4/v4ur:route/v4ur:description" {
    deviate not-supported;
  }
  deviation "/rt:routing/rt:control-plane-protocols/rt:control-plane-protocol/rt:static-routes/v4ur:ipv4/v4ur:route/v4ur:next-hop/v4ur:next-hop-options/v4ur:special-next-hop" {
    deviate not-supported;
  }
  deviation "/rt:routing/rt:control-plane-protocols/rt:control-plane-protocol/rt:static-routes/v4ur:ipv4/v4ur:route/v4ur:next-hop/v4ur:next-hop-options/v4ur:next-hop-list" {
    deviate not-supported;
  }
}
