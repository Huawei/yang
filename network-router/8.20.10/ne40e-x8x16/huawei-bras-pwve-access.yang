/*
Copyright (C) 2019 Huawei Technologies Co., Ltd. All rights reserved.
*/
module huawei-bras-pwve-access {
  namespace urn:huawei:yang:huawei-bras-pwve-access;
  prefix bras-pwve-access;

  import huawei-ifm {
    prefix ifm;
  }
  import huawei-bras-cu-agent {
    prefix bras-cu-agent;
  }
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "Bras PWVE access.";

  revision 2019-11-16 {
    description
      "Initial revision.";
    reference
      "Huawei private.";
  }
  ext:task-name "bras-control";

  container bras-pwve-access {
    description
      "Bras PWVE access.";
    container location-groups {
      description
        "List of the location group.";
      list location-group {
        must "/bras-cu-agent:bras-cu-agent/bras-cu-agent:cu-agent";
        key "name";
        max-elements "256";
        description
          "Configure the location group.";
        leaf name {
          type string {
            length "1..63";
          }
          description
            "The specify name of location group.";
        }
        container interfaces {
          description
            "List of the specify interface.";
          list interface {
            key "name";
            max-elements "32";
            description
              "Configure the specify interface.";
            leaf name {
              type leafref {
                path "/ifm:ifm/ifm:interfaces/ifm:interface/ifm:name";
              }
              must "/ifm:ifm/ifm:interfaces/ifm:interface[ifm:name=current()]/ifm:type='GigabitEthernet' or
                    /ifm:ifm/ifm:interfaces/ifm:interface[ifm:name=current()]/ifm:type='10GE' or
                    /ifm:ifm/ifm:interfaces/ifm:interface[ifm:name=current()]/ifm:type='40GE' or
                    /ifm:ifm/ifm:interfaces/ifm:interface[ifm:name=current()]/ifm:type='100GE' or
                    /ifm:ifm/ifm:interfaces/ifm:interface[ifm:name=current()]/ifm:type='25GE' or
                    /ifm:ifm/ifm:interfaces/ifm:interface[ifm:name=current()]/ifm:type='50GE' or
                    /ifm:ifm/ifm:interfaces/ifm:interface[ifm:name=current()]/ifm:type='50|100GE'";
              must "/ifm:ifm/ifm:interfaces/ifm:interface[ifm:name=current()]/ifm:class='main-interface'";
              description
                "The specify name of interface.";
            }
          }
        }
      }
    }
  }
 
  augment "/ifm:ifm/ifm:interfaces/ifm:interface" {
    description
      "Configure PWVE access to interface model.";
    container pwve-access {
      description
        "Configure PWVE access to interface model.";
      container pwve-interface {
        when "../../ifm:type = 'PW-VE'";
        description
          "Configure PWVE interface.";
        container push-vlan-tag {
          description
            "Configure user VLAN tags.";
          leaf pe-vid {
            type uint16 {
              range "1..4094";
            }
            description
              "Configure PE VLAN ID.";
          }
          leaf ce-vid {
            when "../pe-vid";
            type uint16 {
              range "1..4094";
            }
            description
              "Configure CE VLAN ID.";
          }
        }
        container bind-location-group {
          description
            "Configure the name of location group.";
          leaf name {
            type leafref {
              path "/bras-pwve-access:bras-pwve-access/bras-pwve-access:location-groups/bras-pwve-access:location-group/bras-pwve-access:name";
            }
            description
              "Specify the name of location group.";
          }
        }
      }
    }
  }
}
