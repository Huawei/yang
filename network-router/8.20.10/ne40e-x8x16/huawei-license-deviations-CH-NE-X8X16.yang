/*
Copyright (C) 2020 Huawei Technologies Co., Ltd. All rights reserved.
*/
module huawei-license-deviations-CH-NE-X8X16 {
  namespace "urn:huawei:yang:huawei-license-deviations-CH-NE-X8X16";
  prefix license-devs-CH-NE-X8X16;

  import huawei-license {
    prefix lcs;
  }

  organization
    "Huawei Technologies Co., Ltd.";
  contact
    "Huawei Industrial Base
     Bantian, Longgang
     Shenzhen 518129
     People's Republic of China
     Website: http://www.huawei.com
     Email: support@huawei.com";
  description
    "Proof of permission granted.";

  revision 2020-12-10 {
    description
      "Init revision.";
    reference "Huawei private.";
  }

  deviation "/lcs:license/lcs:license-sale-items/lcs:license-sale-item/lcs:sub-sale-items" {
    deviate not-supported;
  }
}
