/*
Copyright (C) 2019 Huawei Technologies Co., Ltd. All rights reserved.
*/
module huawei-bras-pwve-access-deviations-CH-NE-X8X16 {
  namespace "urn:huawei:yang:huawei-bras-pwve-access-deviations-CH-NE-X8X16";
  prefix bras-pwve-access-devs-CH-NE-X8X16;

  import huawei-bras-pwve-access {
    prefix bras-pwve-access;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-pwve-access module.";

  revision 2019-11-06 {
    description
      "Initial revision.";
    reference "Huawei private.";
  }

  deviation "/ifm:ifm/ifm:interfaces/ifm:interface/bras-pwve-access:pwve-access/bras-pwve-access:pwve-interface/bras-pwve-access:push-vlan-tag" {
    deviate not-supported;
  }
}
