/*
Copyright (C) 2019 Huawei Technologies Co., Ltd. All rights reserved.
*/
module huawei-clocksync-cesacr-deviations-CH-NE-X8X16 {
  namespace "urn:huawei:yang:huawei-clocksync-cesacr-deviations-CH-NE-X8X16";
  prefix clocksync-cesacr-devs-CH-NE-X8X16;

  import huawei-clocksync-cesacr {
    prefix clocksync-cesacr;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-clocksync-cesacr module.";

  revision 2019-11-06 {
    description
      "Initial revision.";
    reference "Huawei private.";
  }

  deviation "/ifm:ifm/ifm:interfaces/ifm:interface/clocksync-cesacr:clock-cesacr/clocksync-cesacr:recovery-modes" {
    deviate not-supported;
  }
}
