/*
Copyright (C) 2020 Huawei Technologies Co., Ltd. All rights reserved.
*/
module huawei-ietf-hardware-deviations-CH-NE-X8X16 {
  namespace "urn:huawei:yang:huawei-ietf-hardware-deviations-CH-NE-X8X16";
  prefix hardware-devs-CH-NE-X8X16;

  import ietf-hardware {
    prefix hw;
  }

  organization
    "Huawei Technologies Co., Ltd.";
  contact
    "Huawei Industrial Base
     Bantian, Longgang
     Shenzhen 518129
     People's Republic of China
     Website: http://www.huawei.com
     Email: support@huawei.com";
  description
    "Configuration deviations of the driver file.";

  revision 2020-04-13 {
    description
      "Initial revision.";
    reference "Huawei private.";
  }

  deviation "/hw:hardware/hw:component" {
    deviate replace {
      config false;
    }
  }
  deviation "/hw:hardware/hw:component/hw:name" {
    deviate replace {
      config false;
    }
  }
  deviation "/hw:hardware/hw:component/hw:state" {
    deviate replace {
      config false;
    }
  }
  deviation "/hw:hardware/hw:component/hw:state/hw:state-last-changed" {
    deviate not-supported;
  }
  deviation "/hw:hardware/hw:component/hw:state/hw:usage-state" {
    deviate not-supported;
  }
  deviation "/hw:hardware/hw:component/hw:sensor-data" {
    deviate not-supported;
  }
  deviation "/hw:hardware-state-change" {
    deviate not-supported;
  }
  deviation "/hw:hardware-state-oper-enabled" {
    deviate not-supported;
  }
  deviation "/hw:hardware-state-oper-disabled" {
    deviate not-supported;
  }
}
