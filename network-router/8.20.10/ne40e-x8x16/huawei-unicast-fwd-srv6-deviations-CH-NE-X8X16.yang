/*
Copyright (C) 2019 Huawei Technologies Co., Ltd. All rights reserved.
*/
module huawei-unicast-fwd-srv6-deviations-CH-NE-X8X16 {
  namespace "urn:huawei:yang:huawei-unicast-fwd-srv6-deviations-CH-NE-X8X16";
  prefix unicast-fwd-srv6-devs-CH-NE-X8X16;

  import huawei-unicast-fwd-srv6 {
    prefix unicast-fwd-srv6;
  }
  import huawei-srv6 {
    prefix srv6;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-unicast-fwd-srv6 module.";

  revision 2019-11-06 {
    description
      "Initial revision.";
    reference "Huawei private.";
  }

  deviation "/ni:network-instance/ni:instances/ni:instance/srv6:srv6/unicast-fwd-srv6:global-ipv6uc-attribute/unicast-fwd-srv6:forward-mode-through" {
    deviate not-supported;
  }
}
