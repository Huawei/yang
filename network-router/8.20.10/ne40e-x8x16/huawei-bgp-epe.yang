/*
Copyright (C) 2020 Huawei Technologies Co., Ltd. All rights reserved.
*/
module huawei-bgp-epe {
  yang-version 1;
  namespace "urn:huawei:yang:huawei-bgp-epe";
  prefix bgp-epe;
  import huawei-network-instance {
    prefix ni;
  }
  import huawei-extension {
    prefix ext;
  }
  import huawei-bgp {
    prefix bgp;
  }
  import huawei-srv6 {
    prefix srv6;
  }
  import ietf-inet-types {
    prefix inet;
  }
  organization
    "Huawei Technologies Co., Ltd.";
  contact
    "Huawei Industrial Base
     Bantian, Longgang
     Shenzhen 518129
     People's Republic of China
     Website: http://www.huawei.com
     Email: support@huawei.com";
  description
    "BGP EPE configuration.";
  revision 2020-03-25 {
    description
      "Initial revision.";
    reference
      "Huawei private.";
  }
  ext:task-name "bgp";
  augment "/ni:network-instance/ni:instances/ni:instance/bgp:bgp/bgp:base-process" {
    description
      "BGP egress engineering segment-routing IPv6 configuration.";
      container epe-srv6 {
        when "../../../ni:name='_public_'";
        description
          "Configure BGP egress engineering segment-routing IPv6 information.";
          leaf locator-name {
            type leafref {
              path "/ni:network-instance/ni:instances/ni:instance/srv6:srv6/srv6:locators/srv6:locator/srv6:name";
            }
            description
              "Referenced locator name.";
          }
      }
    
  }
  augment "/ni:network-instance/ni:instances/ni:instance/bgp:bgp/bgp:base-process/bgp:peers/bgp:peer" {
    description
      "BGP peer egress engineering segment-routing IPv6 configuration.";
    container epe-srv6 {
      when "../../../../../ni:name='_public_' and ../bgp:egress-engineer='enable'";      
      description
        "Configure BGP peer egress engineering segment-routing IPv6 information.";
      choice sid-option {
        description
          "Set automatic SID or static SID.";
        case auto-sid {
          description
            "Set automatic SID.";
          leaf locator-name {
            type leafref {
            path "/ni:network-instance/ni:instances/ni:instance/srv6:srv6/srv6:locators/srv6:locator/srv6:name";
            }
          
            description
              "Name of the locator referenced by a BGP peer.";
          }
        }
        case static-sid {
          when "../../../bgp-epe:epe-srv6/bgp-epe:locator-name";
          description
            "Set static SID value.";
          leaf psp-sid { 
            type inet:ipv6-address-no-zone;
            must "not(../no-psp-usp-sid) or (../psp-sid != ../no-psp-usp-sid)";
            description
              "Static End.X SID (PSP) of a BGP peer.";
            }
          leaf no-psp-usp-sid { 
            type inet:ipv6-address-no-zone;
            must "not(../psp-sid) or (../psp-sid != ../no-psp-usp-sid)";
            description
              "Static End.X SID (no PSP, no USP) of a BGP peer.";
          }
        }
      }
    }
  }
}
