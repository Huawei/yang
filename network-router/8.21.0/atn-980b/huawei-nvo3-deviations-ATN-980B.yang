/*
Copyright (C) 2019-2020 Huawei Technologies Co., Ltd. All rights reserved.
*/
module huawei-nvo3-deviations-ATN-980B {
  yang-version 1;
  namespace "urn:huawei:yang:huawei-nvo3-deviations-ATN-980B";
  prefix nvo3-devs-ATN-980B;

  import huawei-nvo3 {
    prefix nvo3;
  }
  import huawei-evpl {
    prefix evpl;
  }
  import huawei-ifm {
    prefix ifm;
  }
  import huawei-bd {
    prefix bd;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "Management of NVO3.";

  revision 2020-02-11 {
    description
      "The modifications in the schema file are synchronized to the YANG file.";
    reference "Huawei private.";
  }
  revision 2019-03-01 {
    description
      "Initial revision.";
    reference "Huawei private.";
  }

  deviation "/nvo3:nvo3/nvo3:tunnels/nvo3:tunnel/nvo3:mode" {
    deviate not-supported;
  }
  deviation "/evpl:evpl/evpl:instances/evpl:instance/nvo3:nvo3" {
    deviate not-supported;
  }
  deviation "/nvo3:nvo3/nvo3:vni-instances/nvo3:vni-instance/nvo3:static-ipv6-peers" {
    deviate not-supported;
  }
  deviation "/nvo3:nvo3/nvo3:vni-instances/nvo3:vni-instance/nvo3:static-evpl-peers" {
    deviate not-supported;
  }
  deviation "/nvo3:nvo3/nvo3:vni-instances/nvo3:vni-instance/nvo3:static-evpl-ipv6-peers" {
    deviate not-supported;
  }
  deviation "/nvo3:nvo3/nvo3:vteps/nvo3:evpl-peers" {
    deviate not-supported;
  }
  deviation "/nvo3:nvo3/nvo3:vteps/nvo3:cu-peers" {
    deviate not-supported;
  }
  deviation "/nvo3:nvo3/nvo3:tunnels/nvo3:tunnel/nvo3:vpn-name" {
    deviate not-supported;
  }
  deviation "/ifm:ifm/ifm:interfaces/ifm:interface/nvo3:nve/nvo3:attribute/nvo3:source-vtep-ipv6" {
    deviate not-supported;
  }
  deviation "/ifm:ifm/ifm:interfaces/ifm:interface/nvo3:nve/nvo3:attribute/nvo3:bypass-vtep-ipv6" {
    deviate not-supported;
  }
  deviation "/ifm:ifm/ifm:interfaces/ifm:interface/nvo3:nve/nvo3:attribute" {
    deviate delete {
      must '(./source-vtep-ipv6 and ./bypass-vtep-ipv6 and ./source-vtep-ipv6 != ./bypass-vtep-ipv6) or not(./source-vtep-ipv6) or not(./bypass-vtep-ipv6) ';
    }
  }
  deviation "/ifm:ifm/ifm:interfaces/ifm:interface/nvo3:nve/nvo3:attribute/nvo3:source-vtep-ip" {
    deviate add {
      must 'not(/nvo3:nvo3/nvo3:vni-instances/nvo3:vni-instance/nvo3:static-peers/nvo3:static-peer[nvo3:address=current()])';
    }
  }
  deviation "/ifm:ifm/ifm:interfaces/ifm:interface/nvo3:nve/nvo3:attribute/nvo3:bypass-vtep-ip" {
    deviate add {
      must 'not(/nvo3:nvo3/nvo3:vni-instances/nvo3:vni-instance/nvo3:static-peers/nvo3:static-peer[nvo3:address=current()])';
    }
  }
  deviation "/nvo3:nvo3/nvo3:vni-instances/nvo3:vni-instance/nvo3:static-peers/nvo3:static-peer/nvo3:address" {
    deviate add {
      must 'not(/ifm:ifm/ifm:interfaces/ifm:interface/nvo3:nve/nvo3:attribute[nvo3:source-vtep-ip=current()]) and not(/ifm:ifm/ifm:interfaces/ifm:interface/nvo3:nve/nvo3:attribute[nvo3:bypass-vtep-ip=current()])';
    }
  }
  deviation "/ifm:ifm/ifm:interfaces/ifm:interface/nvo3:nve/nvo3:pip" {
    deviate not-supported;
  }
  deviation "/nvo3:nvo3/nvo3:global-attribute" {
    deviate not-supported;
  }
  deviation "/bd:bd/bd:instances/bd:instance/nvo3:nvo3/nvo3:vni-list/nvo3:source-vtep-ip" {
    deviate not-supported;
  }
  deviation "/ni:network-instance/ni:instances/ni:instance/nvo3:nvo3/nvo3:vni-list/nvo3:source-vtep-ip" {
    deviate not-supported;
  }
}
