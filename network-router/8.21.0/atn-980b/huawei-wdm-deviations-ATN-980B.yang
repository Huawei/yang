/*
Copyright (C) 2021 Huawei Technologies Co., Ltd. All rights reserved.
*/
module huawei-wdm-deviations-ATN-980B {
  namespace "urn:huawei:yang:huawei-wdm-deviations-ATN-980B";
  prefix wdm-devs-ATN-980B;

  import huawei-wdm {
    prefix wdm;
  }

  organization
    "Huawei Technologies Co., Ltd.";

  contact
    "Huawei Industrial Base
     Bantian, Longgang
     Shenzhen 518129
     People's Republic of China
     Website: http://www.huawei.com
     Email: support@huawei.com";

  description
    "This module defines deviation statements for huawei-wdm module.";

  revision 2021-05-07 {
    description
      "Initial revision.";
    reference
      "Huawei private.";
  }

  typedef transalarmifdown-alarmtype-deviations {
    type enumeration {
      enum "ODU-AIS" {
        value 22;
        description 
          "ODU-AIS.";
      }
      enum "ODU-LCK" {
        value 23;
        description 
          "ODU-LCK.";
      }
      enum "ODU-OCI" {
        value 24;
        description 
          "ODU-OCI.";
      }
      enum "OTU-AIS" {
        value 25;
        description 
          "OTU-AIS.";
      }
      enum "OTU-LOM" {
        value 26;
        description 
          "OTU-LOM.";
      }
      enum "OTU-SD-BER" {
        value 27;
        description 
          "OTU-SD-BER.";
      }
      enum "OTU-SF-BER" {
        value 28;
        description 
          "OTU-SF-BER.";
      }
      enum "PM-BDI" {
        value 29;
        description 
          "PM-BDI.";
      }
      enum "PM-TIM" {
        value 30;
        description 
          "PM-TIM.";
      }
      enum "R-LOF" {
        value 31;
        description 
          "R-LOF.";
      }
      enum "R-LOS" {
        value 32;
        description 
          "R-LOS.";
      }
      enum "R-OOF" {
        value 33;
        description 
          "R-OOF.";
      }
      enum "SM-BDI" {
        value 34;
        description 
          "SM-BDI.";
      }
      enum "SM-IAE" {
        value 35;
        description 
          "SM-IAE.";
      }
      enum "SM-TIM" {
        value 36;
        description 
          "SM-TIM.";
      }
      enum "PREFEC-TCA" {
        value 37;
        description 
          "PREFEC-TCA.";
      }
      enum "ODU-SD-BER" {
        value 45;
        description 
          "ODU-SD-BER.";
      }
    }
    description 
      "Transmission alarm.";
  }

  typedef wdms-wdm-fecmode-deviations {
    type enumeration {
      enum "standard" {
        value 1;
        description 
          "FEC (G.709).";
      }
      enum "none" {
        value 0;
        description 
          "FEC Disable.";
      }
      enum "enhanced" {
        value 2;
        description 
          "HGFEC (Enhanced).";
      }
      enum "enhanced-i-4" {
        value 3;
        description 
          "AFEC-3 (G.975.1 I.4).";
      }
      enum "enhanced-i-7" {
        value 4;
        description 
          "AFEC (G.975.1 I.7).";
      }
      enum "lhaul-sd" {
        value 5;
        description 
          "Lhaul-sd.";
      }
    }
    description 
      "Fec mode.";
  }

  deviation "/wdm:wdm/wdm:wdms/wdm:wdm/wdm:fecmode" {
    deviate replace {
      type wdm-devs-ATN-980B:wdms-wdm-fecmode-deviations;
    }
  }
  deviation "/wdm:wdm/wdm:wdms/wdm:wdm/wdm:transmission-alarm/wdm:trans-alarm-ifdowns/wdm:trans-alarm-ifdown/wdm:alarm-type" {
    deviate replace {
      type wdm-devs-ATN-980B:transalarmifdown-alarmtype-deviations;
    }
  }

}
