/*
Copyright (C) 2021 Huawei Technologies Co., Ltd. All rights reserved.
*/
module huawei-evpn-ext-deviations-ATN-980B {
  namespace "urn:huawei:yang:huawei-evpn-ext-deviations-ATN-980B";
  prefix evpn-ext-devs-ATN-980B;

  import huawei-evpn-ext {
    prefix evpn-ext;
  }

  import huawei-evpn {
    prefix evpn;
  }

  import huawei-license {
    prefix lcs;
  }

  organization
    "Huawei Technologies Co., Ltd.";

  contact
    "Huawei Industrial Base
     Bantian, Longgang
     Shenzhen 518129
     People's Republic of China
     Website: http://www.huawei.com
     Email: support@huawei.com";

  description
    "This module defines deviation statements for huawei-evpn-ext module.";

  revision 2021-05-07 {
    description
      "Initial revision.";
    reference
      "Huawei private.";
  }

  deviation "/evpn:evpn/evpn-ext:system/evpn-ext:port-select" {
    deviate not-supported;
  }
  deviation "/evpn:evpn/evpn-ext:system/evpn-ext:self-board" {
    deviate not-supported;
  }
  deviation "/evpn:evpn/evpn:instances/evpn:instance/evpn:normal-evpn/evpn-ext:pipe/evpn-ext:color" {
    deviate not-supported;
  }
  deviation "/evpn:evpn/evpn:instances/evpn:instance/evpn:normal-evpn/evpn-ext:reserve-if-switch" {
    deviate not-supported;
  }
  deviation "/evpn:evpn/evpn:instances/evpn:instance/evpn:bd-evpn/evpn-ext:pipe/evpn-ext:color" {
    deviate not-supported;
  }
  deviation "/lcs:license/lcs:license-items/lcs:license-item/evpn-ext:lcs-port-evpns" {
    deviate not-supported;
  }
  deviation "/lcs:license/lcs:license-items/lcs:license-item/evpn-ext:lcs-port-vxlans" {
    deviate not-supported;
  }
  deviation "/lcs:license/evpn-ext:lcs-port-evpns" {
    deviate not-supported;
  }
  deviation "/lcs:license/evpn-ext:lcs-port-vxlans" {
    deviate not-supported;
  }
  deviation "/evpn:evpn/evpn:instances/evpn:instance/evpn:normal-evpn/evpn-ext:pipe/evpn-ext:pipe-mode" {
    deviate delete {
      must "(../split-mode='false') and ((../pipe-mode='pipe' and (../service-class) and (../color)) or (../pipe-mode='shortpipe' and (../service-class) and (../color) and (../domain-name)) or (../pipe-mode='uniform'))";
    }
    deviate add {
      must "(../split-mode='false') and ((../pipe-mode='pipe' and (../service-class)) or (../pipe-mode='shortpipe' and (../service-class) and (../domain-name)) or (../pipe-mode='uniform'))";
    }
  }
  deviation "/evpn:evpn/evpn:instances/evpn:instance/evpn:normal-evpn/evpn-ext:pipe/evpn-ext:ingress-pipe-mode" {
    deviate delete {
      must "((../split-mode='true') and (((../service-class) and (../color) and (../ingress-pipe-mode='shortpipe' or ../ingress-pipe-mode='pipe')) or (../ingress-pipe-mode='uniform' and ../egress-pipe-mode!='uniform')))";
    }
    deviate add {
      must "((../split-mode='true') and (((../service-class) and (../ingress-pipe-mode='shortpipe' or ../ingress-pipe-mode='pipe')) or (../ingress-pipe-mode='uniform' and ../egress-pipe-mode!='uniform')))";
    }
  }
  deviation "/evpn:evpn/evpn:instances/evpn:instance/evpn:bd-evpn/evpn-ext:pipe/evpn-ext:pipe-mode" {
    deviate delete {
      must "(../split-mode='false') and ((../pipe-mode='pipe' and (../service-class) and (../color)) or (../pipe-mode='shortpipe' and (../service-class) and (../color) and (../domain-name)) or (../pipe-mode='uniform'))";
    }
    deviate add {
      must "(../split-mode='false') and ((../pipe-mode='pipe' and (../service-class)) or (../pipe-mode='shortpipe' and (../service-class) and (../domain-name)) or (../pipe-mode='uniform'))";
    }
  }
  deviation "/evpn:evpn/evpn:instances/evpn:instance/evpn:bd-evpn/evpn-ext:pipe/evpn-ext:ingress-pipe-mode" {
    deviate delete {
      must "((../split-mode='true') and (((../service-class) and (../color) and (../ingress-pipe-mode='shortpipe' or ../ingress-pipe-mode='pipe')) or (../ingress-pipe-mode='uniform' and ../egress-pipe-mode!='uniform')))";
    }
    deviate add {
      must "((../split-mode='true') and (((../service-class) and (../ingress-pipe-mode='shortpipe' or ../ingress-pipe-mode='pipe')) or (../ingress-pipe-mode='uniform' and ../egress-pipe-mode!='uniform')))";
    }
  }

}
