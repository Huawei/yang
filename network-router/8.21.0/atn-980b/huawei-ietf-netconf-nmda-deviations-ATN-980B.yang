/*
Copyright (C) 2021 Huawei Technologies Co., Ltd. All rights reserved.
*/
module huawei-ietf-netconf-nmda-deviations-ATN-980B {
  yang-version 1.1;
  namespace "urn:huawei:yang:huawei-ietf-netconf-nmda-deviations-ATN-980B";
  prefix nmda-devs-ATN-980B;

  import ietf-netconf-nmda {
    prefix ncds;
  }

  organization
    "Huawei Technologies Co., Ltd.";
  contact
    "Huawei Industrial Base
     Bantian, Longgang
     Shenzhen 518129
     People's Republic of China
     Website: http://www.huawei.com
     Email: support@huawei.com";
  description
    "Ietf netconf nmda deviation file.";

  revision 2021-01-13 {
    description
      "Initial revision.";
    reference "Huawei private.";
  }

  deviation "/ncds:get-data/ncds:input/ncds:config-filter" {
    deviate not-supported;
  }
  deviation "/ncds:get-data/ncds:input/ncds:origin-filters" {
    deviate not-supported;
  }
  deviation "/ncds:get-data/ncds:input/ncds:max-depth" {
    deviate not-supported;
  }
  deviation "/ncds:get-data/ncds:input/ncds:with-origin" {
    deviate not-supported;
  }
}
