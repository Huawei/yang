/*
Copyright (C) 2021 Huawei Technologies Co., Ltd. All rights reserved.
*/
module huawei-qos-l3vpn-deviations-ATN-980B {
  namespace "urn:huawei:yang:huawei-qos-l3vpn-deviations-ATN-980B";
  prefix qos-l3vpn-devs-ATN-980B;

  import huawei-qos-l3vpn {
    prefix qos-l3vpn;
  }

  import huawei-network-instance {
    prefix ni;
  }

  organization
    "Huawei Technologies Co., Ltd.";

  contact
    "Huawei Industrial Base
     Bantian, Longgang
     Shenzhen 518129
     People's Republic of China
     Website: http://www.huawei.com
     Email: support@huawei.com";

  description
    "This module defines deviation statements for huawei-qos-l3vpn module.";

  revision 2021-05-07 {
    description
      "Initial revision.";
    reference
      "Huawei private.";
  }

  deviation "/ni:network-instance/ni:instances/ni:instance/qos-l3vpn:qos-l3vpn/qos-l3vpn:vxlan-car-disables" {
    deviate not-supported;
  }
  deviation "/ni:network-instance/ni:instances/ni:instance/qos-l3vpn:qos-l3vpn/qos-l3vpn:vxlan-phb/qos-l3vpn:diffserv-domain-name" {
    deviate not-supported;
  }

}
