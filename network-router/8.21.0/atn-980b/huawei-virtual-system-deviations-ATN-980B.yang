/*
Copyright (C) 2021 Huawei Technologies Co., Ltd. All rights reserved.
*/
module huawei-virtual-system-deviations-ATN-980B {
  namespace "urn:huawei:yang:huawei-virtual-system-deviations-ATN-980B";
  prefix vs-devs-ATN-980B;

  import huawei-virtual-system {
    prefix vs;
  }

  organization
    "Huawei Technologies Co., Ltd.";
  contact
    "Huawei Industrial Base
     Bantian, Longgang
     Shenzhen 518129
     People's Republic of China
     Website: http://www.huawei.com
     Email: support@huawei.com";
  description
    "This module defines deviation statements for huawei-virtual-system module.";

  revision 2021-09-16 {
    description
      "Initial revision.";
    reference "Huawei private.";
  }

  deviation "/vs:virtual-system/vs:global" {
    deviate not-supported;
  }
  deviation "/vs:virtual-system/vs:vs-instances/vs:vs-instance/vs:resource" {
    deviate not-supported;
  }
  deviation "/vs:virtual-system/vs:vs-instances/vs:vs-instance/vs:port-mode" {
    deviate not-supported;
  }
}
