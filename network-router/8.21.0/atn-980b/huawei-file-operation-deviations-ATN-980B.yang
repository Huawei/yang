/*
Copyright (C) 2021 Huawei Technologies Co., Ltd. All rights reserved.
*/
module huawei-file-operation-deviations-ATN-980B {
  namespace "urn:huawei:yang:huawei-file-operation-deviations-ATN-980B";
  prefix file-operation-devs-ATN-980B;

  import huawei-file-operation {
    prefix file-operation;
  }

  organization
    "Huawei Technologies Co., Ltd.";
  contact
    "Huawei Industrial Base
     Bantian, Longgang
     Shenzhen 518129
     People's Republic of China
     Website: http://www.huawei.com
     Email: support@huawei.com";
  description
    "This module defines deviation statements for huawei-file-operation module.";

  revision 2021-05-07 {
    description
      "Initial revision.";
    reference "Huawei private.";
  }

  deviation "/file-operation:file-operation/file-operation:disk-usages" {
    deviate not-supported;
  }
  deviation "/file-operation:reset-recycle-bin" {
    deviate not-supported;
  }
  deviation "/file-operation:copy-file/file-operation:input/file-operation:all" {
    deviate not-supported;
  }
  deviation "/file-operation:delete-file/file-operation:input/file-operation:all" {
    deviate not-supported;
  }
}
