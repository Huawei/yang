/*
Copyright (C) 2021 Huawei Technologies Co., Ltd. All rights reserved.
*/
module huawei-license-deviations-ATN-980B {
  namespace "urn:huawei:yang:huawei-license-deviations-ATN-980B";
  prefix lcs-devs-ATN-980B;

  import huawei-license {
    prefix lcs;
  }

  organization
    "Huawei Technologies Co., Ltd.";
  contact
    "Huawei Industrial Base
     Bantian, Longgang
     Shenzhen 518129
     People's Republic of China
     Website: http://www.huawei.com
     Email: support@huawei.com";
  description
    "This module defines deviation statements for huawei-license module.";

  revision 2021-05-07 {
    description
      "Initial revision.";
    reference "Huawei private.";
  }

  deviation "/lcs:license/lcs:global-states/lcs:global-state/lcs:startup-filename" {
    deviate not-supported;
  }
  deviation "/lcs:license/lcs:license-sale-items/lcs:license-sale-item/lcs:sub-sale-items" {
    deviate not-supported;
  }
  deviation "/lcs:license/lcs:stack-sale-items/lcs:stack-sale-item/lcs:license-sale-items/lcs:license-sale-item/lcs:license-items" {
    deviate not-supported;
  }
  deviation "/lcs:license/lcs:license-files/lcs:license-file/lcs:general/lcs:file-expired-date" {
    deviate not-supported;
  }
  deviation "/lcs:license-startup" {
    deviate not-supported;
  }
  deviation "/lcs:license-revoke-chassis/lcs:input/lcs:chassis-id" {
    deviate not-supported;
  }
}
