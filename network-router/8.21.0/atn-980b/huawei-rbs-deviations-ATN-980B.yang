/*
Copyright (C) 2019 Huawei Technologies Co., Ltd. All rights reserved.
*/
module huawei-rbs-deviations-ATN-980B {
  yang-version 1;
  namespace "urn:huawei:yang:huawei-rbs-deviations-ATN-980B";
  prefix rbs-devs-ATN-980B;

  import huawei-rbs {
    prefix rbs;
  }
  import huawei-etrunk {
    prefix etrunk;
  }

  organization
    "Huawei Technologies Co., Ltd.";
  contact
    "Huawei Industrial Base
     Bantian, Longgang
     Shenzhen 518129
     People's Republic of China
     Website: http://www.huawei.com
     Email: support@huawei.com";
  description
    "Remote backup service, providing service backup between the master and backup devices, such as ARP entry backup.";

  revision 2019-04-23 {
    description
      "Initial revision.";
    reference "Huawei private.";
  }

  typedef service-type-deviations {
    type enumeration {
      enum igmp-snooping {
        value 2;
        description
          "IGMP snooping services that can be backed up.";
      }
      enum arp {
        value 5;
        description
          "ARP services that can be backed up.";
      }
      enum igmp {
        value 21;
        description
          "IGMP services that can be backed up.";
      }
      enum dhcp-server {
        value 26;
        description
          "DHCP-SERVER services that can be backed up.";
      }
      enum nd {
        value 32;
        description
          "Nd service that can backed up.";
      }
      enum dhcpv6-relay {
        value 34;
        description
          "DHCPV6 relay services that can backed up.";
      }
    }
    description
      "RBP service type.";
  }

  typedef batch-backup-type-deviations {
    type enumeration {
      enum dhcp-server {
        value 26;
        description
          "DHCP-SERVER services that can be batch backed up.";
      }
      enum dhcpv6-relay {
        value 34;
        description
          "DHCPV6 relay services that can be batch backed up.";
      }
    }
    description
      "Service type batch backup.";
  }

  typedef batch-backup-rpc-type-deviations {
    type enumeration {
      enum all {
        value 0;
        description
          "All services that can be batch backed up now.";
      }
      enum igmp-snooping {
        value 2;
        description
          "IGMP snooping services that can be batch backed up.";
      }
      enum arp {
        value 5;
        description
          "ARP services that can be batch backed up.";
      }
      enum dhcp-server {
        value 26;
        description
          "DHCP-SERVER services that can be batch backed up.";
      }
      enum nd {
        value 32;
        description
          "ND services that can be batch backed up.";
      }
      enum dhcpv6-relay {
        value 34;
        description
          "DHCPV6 relay services that can be batch backed up.";
      }
    }
    description
      "Service type batch backup.";
  }

  deviation "/rbs:rbs/rbs:services/rbs:service/rbs:batch-backups/rbs:batch-backup/rbs:service-type" {
    deviate replace {
      type rbs-devs-ATN-980B:batch-backup-type-deviations;
    }
  }
  deviation "/rbs:batch-backup-now/rbs:input/rbs:service-type" {
    deviate replace {
      type rbs-devs-ATN-980B:batch-backup-rpc-type-deviations;
    }
  }
  deviation "/rbs:rbs/rbs:services/rbs:service/rbs:shut-down" {
    deviate not-supported;
  }
  deviation "/rbs:rbs/rbs:profiles/rbs:profile/rbs:service-types/rbs:service-type/rbs:type" {
    deviate replace {
      type rbs-devs-ATN-980B:service-type-deviations;
    }
  }
  deviation "/rbs:rbs/rbs:profiles/rbs:profile/rbs:name" {
    deviate add {
      must "((../rbs:mode='warm' and not (../rbs:service-types/rbs:service-type[rbs:type='arp']) and not (../rbs:service-types/rbs:service-type[rbs:type='nd']) and not (../rbs:service-types/rbs:service-type[rbs:type='igmp-snooping'])) or (../rbs:mode='hot') or (../rbs:mode='virtual')) and ((../rbs:service-types/rbs:service-type[rbs:type='igmp-snooping'] and not (../rbs:vrrps/rbs:vrrp/rbs:id)) or not (../rbs:service-types/rbs:service-type[rbs:type='igmp-snooping']))";
    }
  }
  deviation "/rbs:rbs/rbs:profiles/rbs:profile/rbs:track-type/rbs:vrrp/rbs:vrrps" {
    deviate add {
      must "((rbs:vrrp[rbs:mac-type='even'] or rbs:vrrp[rbs:mac-type='odd']) and not(../rbs:service-types/rbs:service-type[rbs:type='arp'] or ../rbs:service-types/rbs:service-type[rbs:type='nd'])) or rbs:vrrp[rbs:mac-type='none']";
    }
  }
  deviation "/rbs:rbs/rbs:rbs4-session-car/rbs:cir" {
    deviate replace {
      units "pps";
    }
  }
  deviation "/rbs:rbs/rbs:rbs4-session-car/rbs:cir" {
    deviate replace {
      default "1";
    }
  }
  deviation "/rbs:rbs/rbs:rbs4-session-car/rbs:cir" {
    deviate replace {
      type uint32 {
        range "0..3000";
      }
    }
  }
  deviation "/rbs:rbs/rbs:rbs4-session-car/rbs:cbs" {
    deviate replace {
      units "packet";
    }
  }
  deviation "/rbs:rbs/rbs:rbs4-session-car/rbs:cbs" {
    deviate replace {
      default "3";
    }
  }
  deviation "/rbs:rbs/rbs:rbs4-session-car/rbs:cbs" {
    deviate replace {
      type uint32 {
        range "0..3000";
      }
    }
  }
  deviation "/rbs:rbs/rbs:rbs4-session-car/rbs:pir" {
    deviate replace {
      units "pps";
    }
  }
  deviation "/rbs:rbs/rbs:rbs4-session-car/rbs:pir" {
    deviate replace {
      default "500";
    }
  }
  deviation "/rbs:rbs/rbs:rbs4-session-car/rbs:pir" {
    deviate replace {
      type uint32 {
        range "0..3000";
      }
    }
  }
  deviation "/rbs:rbs/rbs:rbs4-session-car/rbs:pbs" {
    deviate replace {
      units "packet";
    }
  }
  deviation "/rbs:rbs/rbs:rbs4-session-car/rbs:pbs" {
    deviate replace {
      default "750";
    }
  }
  deviation "/rbs:rbs/rbs:rbs4-session-car/rbs:pbs" {
    deviate replace {
      type uint32 {
        range "0..3000";
      }
    }
  }
  deviation "/rbs:rbs/rbs:rbs6-session-car/rbs:cir" {
    deviate replace {
      units "pps";
    }
  }
  deviation "/rbs:rbs/rbs:rbs6-session-car/rbs:cir" {
    deviate replace {
      default "1";
    }
  }
  deviation "/rbs:rbs/rbs:rbs6-session-car/rbs:cir" {
    deviate replace {
      type uint32 {
        range "0..3000";
      }
    }
  }
  deviation "/rbs:rbs/rbs:rbs6-session-car/rbs:cbs" {
    deviate replace {
      units "packet";
    }
  }
  deviation "/rbs:rbs/rbs:rbs6-session-car/rbs:cbs" {
    deviate replace {
      default "3";
    }
  }
  deviation "/rbs:rbs/rbs:rbs6-session-car/rbs:cbs" {
    deviate replace {
      type uint32 {
        range "0..3000";
      }
    }
  }
  deviation "/rbs:rbs/rbs:rbs6-session-car/rbs:pir" {
    deviate replace {
      units "pps";
    }
  }
  deviation "/rbs:rbs/rbs:rbs6-session-car/rbs:pir" {
    deviate replace {
      default "500";
    }
  }
  deviation "/rbs:rbs/rbs:rbs6-session-car/rbs:pir" {
    deviate replace {
      type uint32 {
        range "0..3000";
      }
    }
  }
  deviation "/rbs:rbs/rbs:rbs6-session-car/rbs:pbs" {
    deviate replace {
      units "packet";
    }
  }
  deviation "/rbs:rbs/rbs:rbs6-session-car/rbs:pbs" {
    deviate replace {
      default "750";
    }
  }
  deviation "/rbs:rbs/rbs:rbs6-session-car/rbs:pbs" {
    deviate replace {
      type uint32 {
        range "0..3000";
      }
    }
  }
  deviation "/rbs:rbs/rbs:services/rbs:service/rbs:backup-blocks" {
    deviate not-supported;
  }
  deviation "/etrunk:etrunk/etrunk:instances/etrunk:instance/rbs:rbs" {
    deviate not-supported;
  }
}
