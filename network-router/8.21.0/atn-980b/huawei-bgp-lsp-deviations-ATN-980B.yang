/*
Copyright (C) 2019 Huawei Technologies Co., Ltd. All rights reserved.
*/
module huawei-bgp-lsp-deviations-ATN-980B {
  yang-version 1;
  namespace "urn:huawei:yang:huawei-bgp-lsp-deviations-ATN-980B";
  prefix bgp-lsp-devs-ATN-980B;

  import huawei-bgp-lsp {
    prefix bgp-lsp;
  }
  import huawei-mpls {
    prefix mpls;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2019-03-22 {
    description
      "Initial revision.";
    reference "Huawei private.";
  }

  deviation "/mpls:mpls/mpls:common/mpls:global/bgp-lsp:bgp-ttl-mode" {
    deviate not-supported;
  }
  deviation "/ni:network-instance/ni:instances/ni:instance/mpls:mpls/bgp-lsp:bgp-mpls-lsp/bgp-lsp:bgp-ttl-mode" {
    deviate not-supported;
  }
}
