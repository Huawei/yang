/*
Copyright (C) 2021 Huawei Technologies Co., Ltd. All rights reserved.
*/
module huawei-vaccess-master-deviations-ATN-980B {
  namespace "urn:huawei:yang:huawei-vaccess-master-deviations-ATN-980B";
  prefix vaccess-master-devs-ATN-980B;

  import huawei-network-instance {
    prefix ni;
  }
  import huawei-vaccess-master {
    prefix vaccess-master;
  }

  organization
    "Huawei Technologies Co., Ltd.";
  contact
    "Huawei Industrial Base
     Bantian, Longgang
     Shenzhen 518129
     People's Republic of China
     Website: http://www.huawei.com
     Email: support@huawei.com";
  description
    "Specifies the virtual access model.";

  revision 2021-09-14 {
    description
      "Init revision.";
    reference "Huawei private.";
  }

  deviation "/ni:network-instance/ni:instances/ni:instance/vaccess-master:vaccess-interfaces" {
    deviate not-supported;
  }
}
