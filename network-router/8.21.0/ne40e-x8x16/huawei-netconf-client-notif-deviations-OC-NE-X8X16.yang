/*
Copyright (C) 2021 Huawei Technologies Co., Ltd. All rights reserved.
*/
module huawei-netconf-client-notif-deviations-OC-NE-X8X16 {
  yang-version 1;
  namespace "urn:huawei:yang:huawei-netconf-client-notif-deviations-OC-NE-X8X16";
  prefix netconf-client-notif-devs-OC-NE-X8X16;

  import huawei-netconf-client-notif {
    prefix netconf-client-notif;
  }

  organization
    "Huawei Technologies Co., Ltd.";
  contact
    "Huawei Industrial Base
     Bantian, Longgang
     Shenzhen 518129
     People's Republic of China
     Website: http://www.huawei.com
     Email: support@huawei.com";
  description
    "Notification of netconf-client-notif-deviations-ne40e.";

  revision 2021-04-02 {
    description
      "Initial revision.";
    reference "Huawei private.";
  }

  deviation "/netconf-client-notif:netconf-client-peer-connection-interrupt" {
    deviate not-supported;
  }
  deviation "/netconf-client-notif:netconf-client-peer-connection-resume" {
    deviate not-supported;
  }
}
