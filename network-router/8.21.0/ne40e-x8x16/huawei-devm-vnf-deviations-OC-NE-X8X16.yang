/*
Copyright (C) 2019 Huawei Technologies Co., Ltd. All rights reserved.
*/
module huawei-devm-vnf-deviations-OC-NE-X8X16 {
  namespace "urn:huawei:yang:huawei-devm-vnf-deviations-OC-NE-X8X16";
  prefix devm-vnf-devs-OC-NE-X8X16;

  import huawei-devm-vnf {
    prefix devm-vnf;
  }

  organization
    "Huawei Technologies Co., Ltd.";
  contact
    "Huawei Industrial Base
     Bantian, Longgang
     Shenzhen 518129
     People's Republic of China
     Website: http://www.huawei.com
     Email: support@huawei.com";
  description
    "Global Configuration.";

  revision 2019-08-29 {
    description
      "Initial revision.";
    reference "Huawei private.";
  }

  deviation "/devm-vnf:devm-vnf" {
    deviate not-supported;
  }
}
