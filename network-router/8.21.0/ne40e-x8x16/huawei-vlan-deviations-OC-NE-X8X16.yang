/*
Copyright (C) 2020 Huawei Technologies Co., Ltd. All rights reserved.
*/
module huawei-vlan-deviations-OC-NE-X8X16 {
  namespace "urn:huawei:yang:huawei-vlan-deviations-OC-NE-X8X16";
  prefix vlan-devs-OC-NE-X8X16;

  import huawei-vlan {
    prefix vlan;
  }

  organization
    "Huawei Technologies Co., Ltd.";
  contact
    "Huawei Industrial Base
     Bantian, Longgang
     Shenzhen 518129
     People's Republic of China
     Website: http://www.huawei.com
     Email: support@huawei.com";
  description
    "VLAN management.";

  revision 2020-05-21 {
    description
      "Initial revision.";
    reference "Huawei private.";
  }

  deviation "/vlan:vlan/vlan:vlans/vlan:vlan/vlan:member-ports/vlan:member-port/vlan:tag-mode" {
    deviate not-supported;
  }
}
