/*
Copyright (C) 2021 Huawei Technologies Co., Ltd. All rights reserved.
*/
module huawei-flexe-deviations-OC-NE-X8X16 {
  namespace "urn:huawei:yang:huawei-flexe-deviations-OC-NE-X8X16";
  prefix flexe-devs-OC-NE-X8X16;

  import huawei-flexe {
    prefix flexe;
  }

  organization
    "Huawei Technologies Co., Ltd.";

  contact
    "Huawei Industrial Base
     Bantian, Longgang
     Shenzhen 518129
     People's Republic of China
     Website: http://www.huawei.com
     Email: support@huawei.com";

  description
    "This module defines deviation statements for huawei-flexe module.";

  revision 2021-05-07 {
    description
      "Initial revision.";
    reference
      "Huawei private.";
  }

  deviation "/flexe:flexe/flexe:groups/flexe:group/flexe:padding-enable" {
    deviate delete {
      default "false";
    }
  }

}
