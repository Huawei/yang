/*
Copyright (C) 2019 Huawei Technologies Co., Ltd. All rights reserved.
*/
submodule huawei-diagnostic-tools-common {
  yang-version 1;

  belongs-to huawei-diagnostic-tools {
    prefix diagnostic-tools;
  }

  organization
    "Huawei Technologies Co., Ltd.";
  contact
    "Huawei Industrial Base
     Bantian, Longgang
     Shenzhen 518129
     People's Republic of China
     Website: http://www.huawei.com
     Email: support@huawei.com";
  description
    "Diagnosis tool.";

  revision 2019-04-15 {
    description
      "Initial revision.";
    reference
      "Huawei private.";
  }
  container diagnostic-tools {
    config false;
    description
      "Diagnosis tool, limited to ping and trace.";
  }
}
