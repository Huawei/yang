/*
Copyright (C) 2021 Huawei Technologies Co., Ltd. All rights reserved.
*/
module huawei-bras-dhcp-server-deviations-OC-NE-X8X16 {
  namespace "urn:huawei:yang:huawei-bras-dhcp-server-deviations-OC-NE-X8X16";
  prefix bras-dhcp-server-devs-OC-NE-X8X16;

  import huawei-bras-dhcp-server {
    prefix bras-dhcp-server;
  }

  import huawei-rbs {
    prefix rbs;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-dhcp-server module.";

  revision 2021-05-07 {
    description
      "Initial revision.";
    reference
      "Huawei private.";
  }

  deviation "/bras-dhcp-server:bras-dhcp-server/bras-dhcp-server:dhcp-server-groups/bras-dhcp-server:dhcp-server-group/bras-dhcp-server:remote-backup-service-name" {
    deviate replace {
      type leafref {
        path "/rbs:rbs/rbs:services/rbs:service/rbs:name";
      }
    }
  }

}
