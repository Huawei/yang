/*
Copyright (C) 2021 Huawei Technologies Co., Ltd. All rights reserved.
*/
module huawei-esqm-deviations-OC-NE-X8X16 {
  namespace "urn:huawei:yang:huawei-esqm-deviations-OC-NE-X8X16";
  prefix esqm-devs-OC-NE-X8X16;

  import huawei-esqm {
    prefix esqm;
  }

  import huawei-sflow {
    prefix sflow;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-esqm module.";

  revision 2021-05-07 {
    description
      "Initial revision.";
    reference
      "Huawei private.";
  }

  deviation "/esqm:esqm/esqm:esqm-enable" {
    deviate add {
      must "not(/sflow:sflow/sflow:sflow-enable)";
    }
    deviate add {
      must "count(/devm:devm/devm:lpu-boards/devm:lpu-board[sflow:sflow/sflow:slot-sampling/sflow:enable = 'true']) = 0";
    }
  }

}
