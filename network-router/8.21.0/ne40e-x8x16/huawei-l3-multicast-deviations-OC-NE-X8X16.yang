/*
Copyright (C) 2021 Huawei Technologies Co., Ltd. All rights reserved.
*/
module huawei-l3-multicast-deviations-OC-NE-X8X16 {
  yang-version 1;
  namespace "urn:huawei:yang:huawei-l3-multicast-deviations-OC-NE-X8X16";
  prefix l3mc-devs-OC-NE-X8X16;

  import huawei-network-instance {
    prefix ni;
  }
  import huawei-l3-multicast {
    prefix l3mc;
  }
  import huawei-vaccess-master {
    prefix vaccess-master;
  }
  import huawei-multicast-bas {
    prefix mcbas;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-l3-multicast module.";

  revision 2021-06-08 {
    description
      "Init revision.";
    reference "Huawei private.";
  }

  typedef limit-type-ipv4-deviations {
    type enumeration {
      enum pim-sm-star-group {
        value 1;
        description
          "PIM-SM (*, g).";
      }
      enum pim-sm-source-group {
        value 2;
        description
          "PIM-SM (s, g).";
      }
      enum pim-dm-star-group {
        value 3;
        description
          "PIM-DM (*, g).";
      }
      enum pim-dm-source-group {
        value 4;
        description
          "PIM-DM (s, g).";
      }
    }
    description
      "Limit type.";
  }

  typedef limit-type-ipv6-deviations {
    type enumeration {
      enum pim-sm-star-group {
        value 1;
        description
          "PIM-SM (*, g).";
      }
      enum pim-sm-source-group {
        value 2;
        description
          "PIM-SM (s, g).";
      }
    }
    description
      "Limit type.";
  }

  typedef limit-type-ipv4-vpn-deviations {
    type enumeration {
      enum pim-sm-star-group {
        value 1;
        description
          "PIM-SM (*, g).";
      }
      enum pim-sm-source-group {
        value 2;
        description
          "PIM-SM (s, g).";
      }
    }
    description
      "Limit type.";
  }

  deviation "/ni:network-instance/ni:instances/ni:instance/l3mc:multicast/l3mc:ipv4/l3mc:interface-min-ttls/l3mc:interface-min-ttl" {
    deviate add {
      must 'not(/ni:network-instance/ni:instances/ni:instance/vaccess-master:vaccess-interfaces/vaccess-master:vaccess-interface[vaccess-master:name=current()/name])';
    }
  }
  deviation "/ni:network-instance/ni:instances/ni:instance/l3mc:multicast/l3mc:ipv4/l3mc:interface-track-vrrps/l3mc:interface-track-vrrp" {
    deviate add {
      must 'not(/ni:network-instance/ni:instances/ni:instance/vaccess-master:vaccess-interfaces/vaccess-master:vaccess-interface[vaccess-master:name=current()/name])';
    }
  }
  deviation "/ni:network-instance/ni:instances/ni:instance/l3mc:multicast/l3mc:ipv4/l3mc:limits/l3mc:limit/l3mc:type" {
    deviate replace {
      type l3mc-devs-OC-NE-X8X16:limit-type-ipv4-vpn-deviations;
    }
  }
  deviation "/ni:network-instance/ni:instances/ni:instance/l3mc:multicast/l3mc:ipv6/l3mc:limits/l3mc:limit/l3mc:type" {
    deviate replace {
      type l3mc-devs-OC-NE-X8X16:limit-type-ipv6-deviations;
    }
  }
  deviation "/l3mc:l3-multicast/l3mc:ipv4/l3mc:limits/l3mc:limit/l3mc:type" {
    deviate replace {
      type l3mc-devs-OC-NE-X8X16:limit-type-ipv4-deviations;
    }
  }
  deviation "/l3mc:l3-multicast/l3mc:ipv6/l3mc:limits/l3mc:limit/l3mc:type" {
    deviate replace {
      type l3mc-devs-OC-NE-X8X16:limit-type-ipv6-deviations;
    }
  }
  deviation "/ni:network-instance/ni:instances/ni:instance/l3mc:multicast/l3mc:ipv6/l3mc:interface-boundarys/l3mc:interface-boundary" {
    deviate add {
      must "not(/ifm:ifm/ifm:interfaces/ifm:interface[ifm:name=current()/name]/mcbas:multicast-bas/mcbas:binding-vpn-instances/mcbas:binding-vpn-instance[mcbas:address-family='ipv6-unicast'])";
    }
  }
  deviation "/ni:network-instance/ni:instances/ni:instance/l3mc:multicast/l3mc:ipv4/l3mc:interface-boundarys/l3mc:interface-boundary" {
    deviate add {
      must "not(/ifm:ifm/ifm:interfaces/ifm:interface[ifm:name=current()/name]/mcbas:multicast-bas/mcbas:binding-vpn-instances/mcbas:binding-vpn-instance[mcbas:address-family='ipv4-unicast'])";
    }
  }
}
