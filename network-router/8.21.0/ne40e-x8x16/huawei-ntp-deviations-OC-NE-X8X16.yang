/*
Copyright (C) 2021 Huawei Technologies Co., Ltd. All rights reserved.
*/
module huawei-ntp-deviations-OC-NE-X8X16 {
  namespace "urn:huawei:yang:huawei-ntp-deviations-OC-NE-X8X16";
  prefix ntp-devs-OC-NE-X8X16;

  import huawei-ntp {
    prefix ntp;
  }

  organization
    "Huawei Technologies Co., Ltd.";
  contact
    "Huawei Industrial Base
     Bantian, Longgang
     Shenzhen 518129
     People's Republic of China
     Website: http://www.huawei.com
     Email: support@huawei.com";
  description
    "This module defines deviation statements for huawei-ntp module.";

  revision 2021-05-07 {
    description
      "Initial revision.";
    reference "Huawei private.";
  }

  deviation "/ntp:ntp/ntp:system-config/ntp:max-offset" {
    deviate not-supported;
  }
  deviation "/ntp:ntp/ntp:system-config/ntp:is-auth-password-check" {
    deviate replace {
      default "false";
    }
  }
  deviation "/ntp:ntp/ntp:access-controls/ntp:access-control" {
    deviate add {
      must 'acl4-identity or acl6-identity';
    }
  }
}
