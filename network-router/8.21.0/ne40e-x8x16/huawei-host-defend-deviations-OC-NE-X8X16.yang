/*
Copyright (C) 2020 Huawei Technologies Co., Ltd. All rights reserved.
*/
module huawei-host-defend-deviations-OC-NE-X8X16 {
  namespace "urn:huawei:yang:huawei-host-defend-deviations-OC-NE-X8X16";
  prefix host-defend-devs-OC-NE-X8X16;

  import huawei-host-defend {
    prefix host-defend;
  }
  import huawei-devm {
    prefix devm;
  }

  organization
    "Huawei Technologies Co., Ltd.";
  contact
    "Huawei Industrial Base
     Bantian, Longgang
     Shenzhen 518129
     People's Republic of China
     Website: http://www.huawei.com
     Email: support@huawei.com";
  description
    "Host Defend.";

  revision 2020-02-04 {
    description
      "Initial revision.";
    reference "Huawei private.";
  }

  typedef packet-header-link-type-deviations {
    type enumeration {
      enum ethernet {
        value 1;
        description
          "Ethernet of link type.";
      }
      enum ppp {
        value 2;
        description
          "PPP protocol of link type.";
      }
      enum hdlc {
        value 3;
        description
          "HDLC protocol of link type.";
      }
    }
    description
      "Packet header link type.";
  }

  deviation "/devm:devm/devm:mpu-boards/devm:mpu-board/host-defend:management-plane-defend-slot" {
    deviate not-supported;
  }
  deviation "/host-defend:host-defend/host-defend:fragment-car-stats" {
    deviate not-supported;
  }
  deviation "/host-defend:start-packet-header-obtain/host-defend:input/host-defend:interface-or-link-type/host-defend:link-type-based/host-defend:link-type" {
    deviate replace {
      type host-defend-devs-OC-NE-X8X16:packet-header-link-type-deviations;
    }
  }
  deviation "/host-defend:stop-packet-header-obtain/host-defend:input/host-defend:type/host-defend:condition-based/host-defend:interface-or-link-type/host-defend:link-type-based/host-defend:link-type" {
    deviate replace {
      type host-defend-devs-OC-NE-X8X16:packet-header-link-type-deviations;
    }
  }
}
