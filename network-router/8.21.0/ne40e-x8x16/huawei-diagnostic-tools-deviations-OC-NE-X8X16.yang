/*
Copyright (C) 2020 Huawei Technologies Co., Ltd. All rights reserved.
*/
module huawei-diagnostic-tools-deviations-OC-NE-X8X16 {
  namespace "urn:huawei:yang:huawei-diagnostic-tools-deviations-OC-NE-X8X16";
  prefix diagnostic-tools-devs-OC-NE-X8X16;

  import huawei-diagnostic-tools {
    prefix diagnostic-tools;
  }
  import huawei-y1731 {
    prefix y1731;
  }
  import huawei-l2vpn {
    prefix l2vpn;
  }
  import huawei-network-instance {
    prefix ni;
  }
  import huawei-segment-routing {
    prefix sr;
  }
  import huawei-srpolicy {
    prefix srpolicy;
  }

  organization
    "Huawei Technologies Co., Ltd.";
  contact
    "Huawei Industrial Base
     Bantian, Longgang
     Shenzhen 518129
     People's Republic of China
     Website: http://www.huawei.com
     Email: support@huawei.com";
  description
    "This module defines deviation statements for huawei-diagnostic-tools module.";

  revision 2020-08-28 {
    description
      "Initial revision.";
    reference "Huawei private.";
  }

  typedef pw-type-deviations {
    type enumeration {
      enum atm-trans-cell {
        value 3;
        description
          "ATM transparent cell transport.";
      }
      enum vlan {
        value 4;
        description
          "VLAN encapsulation.";
      }
      enum ethernet {
        value 5;
        description
          "Ethernet encapsulation.";
      }
      enum hdlc {
        value 6;
        description
          "HDLC encapsulation.";
      }
      enum ppp {
        value 7;
        description
          "PPP encapsulation.";
      }
      enum atm-nto1-vcc {
        value 9;
        description
          "ATM n-to-one VCC cell transport.";
      }
      enum atm-nto1-vpc {
        value 10;
        description
          "ATM n-to-one VPC cell transport.";
      }
      enum ip-layer2 {
        value 11;
        description
          "IP-layer2 encapsulation.";
      }
      enum atm-1to1-vcc {
        value 12;
        description
          "ATM one-to-one VCC Cell Mode.";
      }
      enum atm-1to1-vpc {
        value 13;
        description
          "ATM one-to-one VPC Cell Mode.";
      }
      enum cep {
        value 16;
        description
          "CEP encapsulation.";
      }
      enum satop-e1 {
        value 17;
        description
          "Structure-agnostic E1 over Packet.";
      }
      enum cesopsn-basic {
        value 21;
        description
          "CESoPSN basic mode.";
      }
      enum ip-interworking {
        value 64;
        description
          "MPLS L2VPN IP interworking.";
      }
    }
    description
      "Description of pw-type.";
  }

  deviation "/diagnostic-tools:pwe3-start-ping/diagnostic-tools:input/diagnostic-tools:detection-type/diagnostic-tools:vpws-bgp-vpn-instance/diagnostic-tools:vpws-bgp-vpn-name" {
    deviate replace {
      type leafref {
        path "/l2vpn:l2vpn/l2vpn:common/l2vpn:vpws-bgp-vpns/l2vpn:vpws-bgp-vpn/l2vpn:name";
      }
    }
  }
  deviation "/diagnostic-tools:pwe3-start-trace/diagnostic-tools:input/diagnostic-tools:detection-type/diagnostic-tools:vpws-bgp-vpn-instance/diagnostic-tools:vpws-bgp-vpn-name" {
    deviate replace {
      type leafref {
        path "/l2vpn:l2vpn/l2vpn:common/l2vpn:vpws-bgp-vpns/l2vpn:vpws-bgp-vpn/l2vpn:name";
      }
    }
  }
  deviation "/diagnostic-tools:pwe3-start-ping/diagnostic-tools:input/diagnostic-tools:detection-type/diagnostic-tools:pw-id/diagnostic-tools:pw-type" {
    deviate replace {
      type diagnostic-tools-devs-OC-NE-X8X16:pw-type-deviations;
    }
  }
  deviation "/diagnostic-tools:start-lsp-ping/diagnostic-tools:input/diagnostic-tools:lsp-protocol/diagnostic-tools:srbe/diagnostic-tools:flex-algo-id" {
    deviate not-supported;
  }
  deviation "/diagnostic-tools:start-lsp-trace/diagnostic-tools:input/diagnostic-tools:lsp-protocol/diagnostic-tools:srbe/diagnostic-tools:flex-algo-id" {
    deviate not-supported;
  }
  deviation "/diagnostic-tools:vxlan-start-ping" {
    deviate not-supported;
  }
  deviation "/diagnostic-tools:vxlan-stop-ping" {
    deviate not-supported;
  }
  deviation "/diagnostic-tools:vxlan-delete-ping" {
    deviate not-supported;
  }
  deviation "/diagnostic-tools:vxlan-start-trace" {
    deviate not-supported;
  }
  deviation "/diagnostic-tools:vxlan-stop-trace" {
    deviate not-supported;
  }
  deviation "/diagnostic-tools:vxlan-delete-trace" {
    deviate not-supported;
  }
  deviation "/diagnostic-tools:diagnostic-tools/diagnostic-tools:vxlan" {
    deviate not-supported;
  }
  deviation "/diagnostic-tools:start-lb-test/diagnostic-tools:input/diagnostic-tools:md-name" {
    deviate replace {
      type leafref {
        path "/y1731:y1731/y1731:global-enable/y1731:mds/y1731:md/y1731:name";
      }
    }
  }
  deviation "/diagnostic-tools:start-lb-test/diagnostic-tools:input/diagnostic-tools:ma-name" {
    deviate replace {
      type leafref {
        path "/y1731:y1731/y1731:global-enable/y1731:mds/y1731:md[y1731:name=current()/../md-name]/y1731:mas/y1731:ma/y1731:name";
      }
    }
  }
  deviation "/diagnostic-tools:start-lb-test/diagnostic-tools:input/diagnostic-tools:mep-id" {
    deviate replace {
      type leafref {
        path "/y1731:y1731/y1731:global-enable/y1731:mds/y1731:md[y1731:name=current()/../md-name]/y1731:mas/y1731:ma[y1731:name=current()/../ma-name]/y1731:meps/y1731:mep/y1731:id";
      }
    }
  }
  deviation "/diagnostic-tools:start-lb-test/diagnostic-tools:input/diagnostic-tools:remote/diagnostic-tools:remote-mep-id/diagnostic-tools:rmep-id" {
    deviate replace {
      type leafref {
        path "/y1731:y1731/y1731:global-enable/y1731:mds/y1731:md[y1731:name=current()/../md-name]/y1731:mas/y1731:ma[y1731:name=current()/../ma-name]/y1731:rmeps/y1731:rmep/y1731:id";
      }
    }
  }
  deviation "/diagnostic-tools:start-lt-test/diagnostic-tools:input/diagnostic-tools:md-name" {
    deviate replace {
      type leafref {
        path "/y1731:y1731/y1731:global-enable/y1731:mds/y1731:md/y1731:name";
      }
    }
  }
  deviation "/diagnostic-tools:start-lt-test/diagnostic-tools:input/diagnostic-tools:ma-name" {
    deviate replace {
      type leafref {
        path "/y1731:y1731/y1731:global-enable/y1731:mds/y1731:md[y1731:name=current()/../md-name]/y1731:mas/y1731:ma/y1731:name";
      }
    }
  }
  deviation "/diagnostic-tools:start-lt-test/diagnostic-tools:input/diagnostic-tools:mep-id" {
    deviate replace {
      type leafref {
        path "/y1731:y1731/y1731:global-enable/y1731:mds/y1731:md[y1731:name=current()/../md-name]/y1731:mas/y1731:ma[y1731:name=current()/../ma-name]/y1731:meps/y1731:mep/y1731:id";
      }
    }
  }
  deviation "/diagnostic-tools:start-lt-test/diagnostic-tools:input/diagnostic-tools:remote/diagnostic-tools:remote-mep-id/diagnostic-tools:rmep-id" {
    deviate replace {
      type leafref {
        path "/y1731:y1731/y1731:global-enable/y1731:mds/y1731:md[y1731:name=current()/../md-name]/y1731:mas/y1731:ma[y1731:name=current()/../ma-name]/y1731:rmeps/y1731:rmep/y1731:id";
      }
    }
  }
  deviation "/diagnostic-tools:pwe3-start-trace/diagnostic-tools:input/diagnostic-tools:detection-type/diagnostic-tools:pw-id/diagnostic-tools:pw-type" {
    deviate replace {
      type diagnostic-tools-devs-OC-NE-X8X16:pw-type-deviations;
    }
  }
  deviation "/diagnostic-tools:vpls-start-vsi-ping/diagnostic-tools:input/diagnostic-tools:vsi-name" {
    deviate replace {
      type leafref {
        path "/l2vpn:l2vpn/l2vpn:instances/l2vpn:instance/l2vpn:name";
      }
    }
  }
  deviation "/diagnostic-tools:start-lsp-ping/diagnostic-tools:input/diagnostic-tools:lsp-protocol/diagnostic-tools:srte-policy/diagnostic-tools:probe-type/diagnostic-tools:policy-name/diagnostic-tools:policy-name" {
    deviate replace {
      type leafref {
        path "/ni:network-instance/ni:instances/ni:instance/sr:segment-routing/srpolicy:srpolicy/srpolicy:policys/srpolicy:policy/srpolicy:name";
      }
    }
  }
  deviation "/diagnostic-tools:start-lsp-trace/diagnostic-tools:input/diagnostic-tools:lsp-protocol/diagnostic-tools:srte-policy/diagnostic-tools:probe-type/diagnostic-tools:policy-name/diagnostic-tools:policy-name" {
    deviate replace {
      type leafref {
        path "/ni:network-instance/ni:instances/ni:instance/sr:segment-routing/srpolicy:srpolicy/srpolicy:policys/srpolicy:policy/srpolicy:name";
      }
    }
  }
}
