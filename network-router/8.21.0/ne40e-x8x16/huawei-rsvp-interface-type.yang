/*
Copyright (C) 2019-2020 Huawei Technologies Co., Ltd. All rights reserved.
*/
submodule huawei-rsvp-interface-type {
  belongs-to huawei-rsvp-interface {
    prefix rsvp-interface;
  }
  organization
    "Huawei Technologies Co., Ltd.";
  contact
    "Huawei Industrial Base
     Bantian, Longgang
     Shenzhen 518129
     People's Republic of China
     Website: http://www.huawei.com
     Email: support@huawei.com";
  description
    "Specifies the multi-protocol label switching protocol.";
  revision 2020-03-10 {
    description
      "Fixed some descriptions.";
    reference
      "Huawei private.";
  }
  revision 2019-07-29 {
    description
      "Init revision.";
    reference
      "Huawei private.";
  }
  /*
   * typedef-stmt
   */
  typedef frr-mode-type {
    type enumeration {
      enum "default" {
        value 0;
        description
          "Inherit from global configuration defaultly.";
      }
      enum "link" {
        value 1;
        description
          "Link protection mode.";
      }
      enum "node" {
        value 2;
        description
          "Node protection mode.";
      }
      enum "self-adapting" {
        value 3;
        description
          "Self-adapting protection mode.";
      }
      enum "disable" {
        value 4;
        description
          "No protection.";
      }
    }
    description
      "RSVP TE FRR mode.";
  }
  typedef rsvp-authentication-type {
    type enumeration {
      enum "md5" {
        value 0;
        description
          "Set ciphertext MD5.";
      }
      enum "md5-plain" {
        value 1;
        description
          "Set simple text MD5.";
      }
      enum "keychain" {
        value 2;
        description
          "Keychain authentication.";
      }
    }
    description
      "TE authentication type.";
  }
}
