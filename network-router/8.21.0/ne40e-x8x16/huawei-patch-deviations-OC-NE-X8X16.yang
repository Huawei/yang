/*
Copyright (C) 2021 Huawei Technologies Co., Ltd. All rights reserved.
*/
module huawei-patch-deviations-OC-NE-X8X16 {
  namespace "urn:huawei:yang:huawei-patch-deviations-OC-NE-X8X16";
  prefix patch-devs-OC-NE-X8X16;

  import huawei-patch {
    prefix patch;
  }

  organization
    "Huawei Technologies Co., Ltd.";
  contact
    "Huawei Industrial Base
     Bantian, Longgang
     Shenzhen 518129
     People's Republic of China
     Website: http://www.huawei.com
     Email: support@huawei.com";
  description
    "This module defines deviation statements for huawei-patch module.";

  revision 2021-05-07 {
    description
      "Initial revision.";
    reference "Huawei private.";
  }

  deviation "/patch:patch/patch:cpu-usage-thresholds" {
    deviate not-supported;
  }
  deviation "/patch:patch/patch:next-startup-patchs" {
    deviate not-supported;
  }
  deviation "/patch:patch/patch:operation-schedules/patch:operation-schedule/patch:name" {
    deviate not-supported;
  }
  deviation "/patch:patch/patch:operation-schedules/patch:operation-schedule/patch:fail-reason" {
    deviate not-supported;
  }
  deviation "/patch:patch/patch:download-package-schedule" {
    deviate not-supported;
  }
  deviation "/patch:patch/patch:download-package-load-path" {
    deviate not-supported;
  }
  deviation "/patch:download-patch-file" {
    deviate not-supported;
  }
  deviation "/patch:check-patch" {
    deviate not-supported;
  }
}
