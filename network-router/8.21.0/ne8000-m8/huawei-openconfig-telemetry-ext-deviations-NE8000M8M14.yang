/*
Copyright (C) 2021 Huawei Technologies Co., Ltd. All rights reserved.
*/
module huawei-openconfig-telemetry-ext-deviations-NE8000M8M14 {
  namespace "urn:huawei:yang:huawei-openconfig-telemetry-ext-deviations-NE8000M8M14";
  prefix hw-telemetry-ext-devs-NE8000M8M14;

  import huawei-openconfig-telemetry-ext {
    prefix hw-telemetry-ext;
  }
  import openconfig-telemetry {
    prefix ot;
  }

  organization
    "Huawei Technologies Co., Ltd.";
  contact
    "Huawei Industrial Base
     Bantian, Longgang
     Shenzhen 518129
     People's Republic of China
     Website: http://www.huawei.com
     Email: support@huawei.com";
  description
    "This module defines deviation statements for huawei-openconfig-telemetry-ext module.";

  revision 2021-05-07 {
    description
      "Initial revision.";
    reference "Huawei private.";
  }

  deviation "/ot:telemetry-system/hw-telemetry-ext:global/hw-telemetry-ext:config/hw-telemetry-ext:json-only-content" {
    deviate not-supported;
  }
  deviation "/ot:telemetry-system/hw-telemetry-ext:global/hw-telemetry-ext:state/hw-telemetry-ext:json-only-content" {
    deviate not-supported;
  }
}
