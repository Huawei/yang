/*
Copyright (C) 2019 Huawei Technologies Co., Ltd. All rights reserved.
*/
module huawei-ospfv2-deviations-NE8000M8M14 {
  namespace "urn:huawei:yang:huawei-ospfv2-deviations-NE8000M8M14";
  prefix ospfv2-devs-NE8000M8M14;

  import huawei-ospfv2 {
    prefix ospfv2;
  }
  import huawei-network-instance {
    prefix ni;
  }
  import huawei-l3vpn {
    prefix l3vpn;
  }
  import huawei-mpls {
    prefix mpls;
  }
  import huawei-mpls-ldp {
    prefix mpls-ldp;
  }

  organization
    "Huawei Technologies Co., Ltd.";
  contact
    "Huawei Industrial Base
     Bantian, Longgang
     Shenzhen 518129
     People's Republic of China
     Website: http://www.huawei.com
     Email: support@huawei.com";
  description
    "OSPFv2 management.";

  revision 2019-04-04 {
    description
      "Initial revision.";
    reference "Huawei private.";
  }

  deviation "/ospfv2:ospfv2/ospfv2:advertise-max-cost" {
    deviate not-supported;
  }
  deviation "/ni:network-instance/ni:instances/ni:instance/ospfv2:ospfv2/ospfv2:sites/ospfv2:site/ospfv2:shutdown" {
    deviate not-supported;
  }
  deviation "/ni:network-instance/ni:instances/ni:instance/l3vpn:afs/l3vpn:af/ospfv2:ospf-import-rts/ospfv2:ospf-import-rt/ospfv2:src-vrf" {
    deviate add {
      must "(../../../l3vpn:type='ipv4-unicast' and /ni:network-instance/ni:instances/ni:instance[ni:name=current()]/l3vpn:afs/l3vpn:af[l3vpn:type='ipv4-unicast'])";
    }
  }
  deviation "/ni:network-instance/ni:instances/ni:instance/ospfv2:ospfv2/ospfv2:sites/ospfv2:site/ospfv2:areas/ospfv2:area/ospfv2:interfaces/ospfv2:interface/ospfv2:source-sub-ip-address" {
    deviate not-supported;
  }
  deviation "/ni:network-instance/ni:instances/ni:instance/ospfv2:ospfv2/ospfv2:sites/ospfv2:site/ospfv2:cost-bindings" {
    deviate not-supported;
  }
  deviation "/ni:network-instance/ni:instances/ni:instance/ospfv2:ospfv2/ospfv2:sites/ospfv2:site/ospfv2:bier" {
    deviate not-supported;
  }
  deviation "/ni:network-instance/ni:instances/ni:instance/ospfv2:ospfv2/ospfv2:sites/ospfv2:site/ospfv2:mpls-ldp-auto-flag" {
    deviate add {
      must "/mpls:mpls/mpls-ldp:ldp/mpls-ldp:enable='true' and ../../../../ni:name='_public_' or ../mpls-ldp-auto-flag='none'";
    }
  }
  deviation "/ni:network-instance/ni:instances/ni:instance/ospfv2:ospfv2/ospfv2:sites/ospfv2:site/ospfv2:vlink-nbr-statistics" {
    deviate not-supported;
  }
  deviation "/ospfv2:ospfv2/ospfv2:global-state" {
    deviate not-supported;
  }
  deviation "/ospfv2:reset-redistribution" {
    deviate not-supported;
  }
  deviation "/ospfv2:reset-counter" {
    deviate not-supported;
  }
  deviation "/ospfv2:reset-process" {
    deviate not-supported;
  }
  deviation "/ospfv2:reset-peer" {
    deviate not-supported;
  }
  deviation "/ospfv2:reset-spf" {
    deviate not-supported;
  }
  deviation "/ospfv2:reset-frr" {
    deviate not-supported;
  }
  deviation "/ospfv2:reset-suppress-peer" {
    deviate not-supported;
  }
  deviation "/ni:network-instance/ni:instances/ni:instance/ospfv2:ospfv2/ospfv2:sites/ospfv2:site/ospfv2:mpls-te-statistics" {
    deviate not-supported;
  }
}
