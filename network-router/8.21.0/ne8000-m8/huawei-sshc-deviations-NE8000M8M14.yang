/*
Copyright (C) 2021 Huawei Technologies Co., Ltd. All rights reserved.
*/
module huawei-sshc-deviations-NE8000M8M14 {
  namespace "urn:huawei:yang:huawei-sshc-deviations-NE8000M8M14";
  prefix sshc-devs-NE8000M8M14;

  import huawei-sshc {
    prefix sshc;
  }

  organization
    "Huawei Technologies Co., Ltd.";
  contact
    "Huawei Industrial Base
     Bantian, Longgang
     Shenzhen 518129
     People's Republic of China
     Website: http://www.huawei.com
     Email: support@huawei.com";
  description
    "This module defines deviation statements for huawei-sshc module.";

  revision 2021-05-07 {
    description
      "Initial revision.";
    reference "Huawei private.";
  }

  typedef sshc-pubkey-type-deviations {
    type enumeration {
      enum RSA {
        value 1;
        description
          "RSA client public key.";
      }
      enum DSA {
        value 2;
        description
          "DSA client public key.";
      }
      enum ECC {
        value 3;
        description
          "ECC client public key.";
      }
    }
    description
      "SSH client public key encryption type list.";
  }

  deviation "/sshc:sshc/sshc:client/sshc:pki-domain" {
    deviate not-supported;
  }
  deviation "/sshc:sshc/sshc:kex-alg/sshc:dh-group18-sha512" {
    deviate not-supported;
  }
  deviation "/sshc:sshc/sshc:kex-alg/sshc:curve25519-sha256" {
    deviate not-supported;
  }
  deviation "/sshc:sshc/sshc:pubkey-alg/sshc:x509v3-ssh-rsa" {
    deviate not-supported;
  }
  deviation "/sshc:sshc/sshc:session-car" {
    deviate not-supported;
  }
  deviation "/sshc:tcp-port-forwarding" {
    deviate not-supported;
  }
  deviation "/sshc:sshc/sshc:kex-alg" {
    deviate add {
      must "../kex-alg/dh-group-exchange-sha-256 = 'true' or ../kex-alg/dh-group-exchange-sha1 = 'true' or ../kex-alg/dh-group1-sha1 = 'true' or ../kex-alg/ecdh-sha2-nistp-256 = 'true' or ../kex-alg/ecdh-sha2-nistp-384 = 'true' or ../kex-alg/ecdh-sha2-nistp-521 = 'true' or ../kex-alg/sm2-kep = 'true' or ../kex-alg/dh-group14-sha1 = 'true' or ../kex-alg/dh-group16-sha512 = 'true'";
    }
    deviate delete {
      must "../kex-alg/dh-group-exchange-sha-256 = 'true' or ../kex-alg/dh-group-exchange-sha1 = 'true' or ../kex-alg/dh-group1-sha1 = 'true' or ../kex-alg/ecdh-sha2-nistp-256 = 'true' or ../kex-alg/ecdh-sha2-nistp-384 = 'true' or ../kex-alg/ecdh-sha2-nistp-521 = 'true' or ../kex-alg/sm2-kep = 'true' or ../kex-alg/dh-group14-sha1 = 'true' or ../kex-alg/dh-group16-sha512 = 'true' or ../kex-alg/dh-group18-sha512 = 'true' or ../kex-alg/curve25519-sha256 = 'true'";
    }
  }
  deviation "/sshc:sshc/sshc:pubkey-alg" {
    deviate add {
      must "../pubkey-alg/dsa = 'true' or ../pubkey-alg/ecc = 'true' or ../pubkey-alg/rsa = 'true' or ../pubkey-alg/sm2 = 'true' or ../pubkey-alg/rsa-sha2-256 = 'true' or ../pubkey-alg/rsa-sha2-512 = 'true'";
    }
    deviate delete {
      must "../pubkey-alg/dsa = 'true' or ../pubkey-alg/ecc = 'true' or ../pubkey-alg/rsa = 'true' or ../pubkey-alg/sm2 = 'true' or ../pubkey-alg/x509v3-ssh-rsa = 'true' or ../pubkey-alg/rsa-sha2-256 = 'true' or ../pubkey-alg/rsa-sha2-512 = 'true'";
    }
  }
}
