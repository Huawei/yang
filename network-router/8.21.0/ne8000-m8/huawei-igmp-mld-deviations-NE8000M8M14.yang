/*
Copyright (C) 2021 Huawei Technologies Co., Ltd. All rights reserved.
*/
module huawei-igmp-mld-deviations-NE8000M8M14 {
  namespace "urn:huawei:yang:huawei-igmp-mld-deviations-NE8000M8M14";
  prefix igmp-mld-devs-NE8000M8M14;

  import huawei-igmp-mld {
    prefix igmp-mld;
  }
  import huawei-rbs {
    prefix rbs;
  }
  import huawei-multicast {
    prefix mc;
  }

  organization
    "Huawei Technologies Co., Ltd.";
  contact
    "Huawei Industrial Base
     Bantian, Longgang
     Shenzhen 518129
     People's Republic of China
     Website: http://www.huawei.com
     Email: support@huawei.com";
  description
    "This module defines deviation statements for huawei-igmp-mld module.";

  revision 2021-05-07 {
    description
      "Initial revision.";
    reference "Huawei private.";
  }

  deviation "/mc:multicast/igmp-mld:igmp/igmp-mld:disable-dhcp-stb-packet-copys/igmp-mld:disable-dhcp-stb-packet-copy/igmp-mld:rbp-name" {
    deviate replace {
      type leafref {
        path "/rbs:rbs/rbs:profiles/rbs:profile/rbs:name";
      }
    }
    deviate add {
      must "/rbs:rbs/rbs:profiles/rbs:profile[rbs:name=current()]/rbs:service-types/rbs:service-type[rbs:type='multicast']";
    }
  }
}
