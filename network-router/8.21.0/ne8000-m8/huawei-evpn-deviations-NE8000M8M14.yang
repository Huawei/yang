/*
Copyright (C) 2019 Huawei Technologies Co., Ltd. All rights reserved.
*/
module huawei-evpn-deviations-NE8000M8M14 {
  namespace "urn:huawei:yang:huawei-evpn-deviations-NE8000M8M14";
  prefix evpn-devs-NE8000M8M14;

  import huawei-evpn {
    prefix evpn;
  }
  import huawei-network-instance {
    prefix ni;
  }
  import huawei-l3vpn {
    prefix l3vpn;
  }
  import huawei-ifm {
    prefix ifm;
  }
  import huawei-nvo3 {
    prefix nvo3;
  }
  import huawei-evpl {
    prefix evpl;
  }
  import huawei-vrrp {
    prefix vrrp;
  }
  import huawei-ip {
    prefix ip;
  }
  import huawei-mac {
    prefix mac;
  }
  import huawei-bd {
    prefix bd;
  }
  import huawei-l2vpn {
    prefix l2vpn;
  }

  organization
    "Huawei Technologies Co., Ltd.";
  contact
    "Huawei Industrial Base
     Bantian, Longgang
     Shenzhen 518129
     People's Republic of China
     Website: http://www.huawei.com
     Email: support@huawei.com";
  description
    "EVPN configuration.";

  revision 2019-03-22 {
    description
      "Initial revision.";
    reference "Huawei private.";
  }

  deviation "/evpn:evpn/evpn:site/evpn:ad-per-es-split" {
    deviate not-supported;
  }
  deviation "/evpn:evpn/evpn:site/evpn:alm-threshold" {
    deviate not-supported;
  }
  deviation "/evpn:evpn/evpn:site/evpn:irb-reoriginated" {
    deviate not-supported;
  }
  deviation "/evpn:evpn/evpn:site/evpn:irb-split-group" {
    deviate not-supported;
  }
  deviation "/evpn:evpn/evpn:site/evpn:recovery-percentage" {
    deviate not-supported;
  }
  deviation "/ni:network-instance/ni:instances/ni:instance/l3vpn:afs/l3vpn:af/evpn:evpn/evpn:irb2ip" {
    deviate not-supported;
  }
  deviation "/evpn:evpn/evpn:base-process/evpn:source-address" {
    deviate add {
      must 'not(/ifm:ifm/ifm:interfaces/ifm:interface/nvo3:nve/nvo3:attribute[nvo3:source-vtep-ip=current()]) and not(/ifm:ifm/ifm:interfaces/ifm:interface/nvo3:nve/nvo3:attribute[nvo3:bypass-vtep-ip=current()])';
    }
  }
  deviation "/evpn:evpn/evpn:base-process/evpn:evpn-overlay" {
    deviate not-supported;
  }
  deviation "/evpl:evpl/evpl:instances/evpl:instance/evpn:evpn/evpn:vrrp" {
    deviate add {
      must "(not(../../evpl:interfaces/evpl:interface/evpl:name) or (/ifm:ifm/ifm:interfaces/ifm:interface[ifm:name=current()/../../evpl:interfaces/evpl:interface/evpl:name]/ifm:type = 'Virtual-Ethernet')) and ((current()/version='vrrp' and /ifm:ifm/ifm:interfaces/ifm:interface[ifm:name=current()/interface-name]/ip:ipv4/vrrp:vrrp/vrrp:groups/vrrp:group[vrrp:id=current()/id]) or (current()/version='vrrp6' and /ifm:ifm/ifm:interfaces/ifm:interface[ifm:name=current()/interface-name]/ip:ipv6/vrrp:vrrp6/vrrp:group6s/vrrp:group6[vrrp:id=current()/id]))";
    }
  }
  deviation "/bd:bd/bd:instances/bd:instance/evpn:evpn/evpn:umr-originate" {
    deviate delete {
      must "(../umr-originate='true' and not(../../nvo3:nvo3/nvo3:vni-list/nvo3:vni) and not(/l2vpn:l2vpn/l2vpn:instances/l2vpn:instance/l2vpn:vpls/l2vpn:bds/l2vpn:bd[l2vpn:id=current()/../../bd:id]) and (../../bd:mac-learn-style!='qualify')) or (../umr-originate='false')";
    }
    deviate add {
      must "(../umr-originate='true' and not(../../nvo3:nvo3/nvo3:vni-list/nvo3:vni) and not(/l2vpn:l2vpn/l2vpn:instances/l2vpn:instance/l2vpn:vpls/l2vpn:bds/l2vpn:bd[l2vpn:id=current()/../../bd:id]) and (../../bd:mac-learn-style!='qualify') and not(../../mac:mac-addresss/mac:mac-address[mac:address = '0000-0000-0000'])) or (../umr-originate='false')";
    }
  }
}
