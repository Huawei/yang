/*
Copyright (C) 2021 Huawei Technologies Co., Ltd. All rights reserved.
*/
module huawei-loopdetect-deviations-NE8000M8M14 {
  namespace "urn:huawei:yang:huawei-loopdetect-deviations-NE8000M8M14";
  prefix loopdetect-devs-NE8000M8M14;

  import huawei-loopdetect {
    prefix loopdetect;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-loopdetect module.";

  revision 2021-05-07 {
    description
      "Initial revision.";
    reference
      "Huawei private.";
  }

  deviation "/loopdetect:loopdetect/loopdetect:trigger-detect/loopdetect:global/loopdetect:min-port-up-time" {
    deviate replace {
      type uint32 {
        range "1..100";
      }
    }
  }
  deviation "/ifm:ifm/ifm:interfaces/ifm:interface/loopdetect:loopdetect/loopdetect:loopback-detect/loopdetect:block-time" {
    deviate replace {
      type uint32 {
        range "5..255";
      }
    }
  }

}
