/*
Copyright (C) 2021 Huawei Technologies Co., Ltd. All rights reserved.
*/
module huawei-pbr-notification-deviations-NE8000M8M14 {
  namespace "urn:huawei:yang:huawei-pbr-notification-deviations-NE8000M8M14";
  prefix pbr-notification-devs-NE8000M8M14;

  import huawei-pbr-notification {
    prefix pbr-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-pbr-notification module.";

  revision 2021-05-07 {
    description
      "Initial revision.";
    reference
      "Huawei private.";
  }

  deviation "/pbr-notification:xqos-interface-down-redirect-next-hop-invalid-alarm" {
    deviate not-supported;
  }
  deviation "/pbr-notification:xqos-interface-down-redirect-next-hop-invalid-alarm-clear" {
    deviate not-supported;
  }
  deviation "/pbr-notification:xqos-redirect-next-hop-event-log" {
    deviate not-supported;
  }

}
