/*
Copyright (C) 2019 Huawei Technologies Co., Ltd. All rights reserved.
*/
module huawei-flowspec-deviations-NE8000M8M14 {
  namespace "urn:huawei:yang:huawei-flowspec-deviations-NE8000M8M14";
  prefix flowspec-devs-NE8000M8M14;

  import huawei-flowspec {
    prefix flowspec;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2019-09-09 {
    description
      "Initial revision.";
    reference "Huawei private.";
  }

  deviation "/ni:network-instance/ni:instances/ni:instance/flowspec:flowspec/flowspec:flow-routes/flowspec:flow-route/flowspec:condition/flowspec:origin-ass" {
    deviate not-supported;
  }
  deviation "/flowspec:flowspec/flowspec:interface-groups" {
    deviate not-supported;
  }
  deviation "/ni:network-instance/ni:instances/ni:instance/flowspec:flowspec/flowspec:flow-routes/flowspec:flow-route/flowspec:interface-groups" {
    deviate not-supported;
  }
}
