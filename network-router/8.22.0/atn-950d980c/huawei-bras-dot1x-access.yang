/*
Copyright (C) 2019-2021 Huawei Technologies Co., Ltd. All rights reserved.
*/
module huawei-bras-dot1x-access {
  namespace "urn:huawei:yang:huawei-bras-dot1x-access";
  prefix bras-dot1x-access;
  import huawei-ifm {
    prefix ifm;
  }
  import huawei-bras-basic-access {
    prefix bras-basic-access;
  }
  import huawei-pub-type {
    prefix pub-type;
  }
  import huawei-extension {
    prefix ext;
  }
  ext:task-name "bas-eap";
  organization
    "Huawei Technologies Co., Ltd.";
  contact
    "Huawei Industrial Base
     Bantian, Longgang
     Shenzhen 518129
     People's Republic of China
     Website: http://www.huawei.com
     Email: support@huawei.com";
  description
    "Configure the dot1x access.";
  revision 2021-12-29 {
    description
      "Description modification.";
    reference
      "Huawei private.";
  }
  revision 2019-03-26 {
    description
      "Initial revision.";
    reference
      "Huawei private.";
  }
/****************************type definitions*************************************/
  typedef dot1x-user-state {
    type enumeration {
      enum "idle" {
        value 0;
        description
          "Idle.";
      }
      enum "initial" {
        value 1;
        description
          "Initializing.";
      }
      enum "connecting" {
        value 2;
        description
          "Connecting.";
      }
      enum "response" {
        value 3;
        description
          "Waiting for an authentication response.";
      }
      enum "request" {
        value 4;
        description
          "Processing challenge messages.";
      }
      enum "authenticated" {
        value 5;
        description
          "Successfully authenticated.";
      }
      enum "being-offline" {
        value 6;
        description
          "User logout.";
      }
      enum "wrong-status" {
        value 7;
        description
          "Wrong status.";
      }
    }
    description
      "Current EAPoL state machine status of a user.";
  }
  typedef port-current-state {
    type enumeration {
      enum "un-authorized" {
        value 0;
        description
          " The interface is in the unauthorized status.";
      }
      enum "authorized" {
        value 1;
        description
          "The interface is in the authorized status.";
      }
    }
    description
      "Current authorization status of an interface.";
  }
/*****************************type definitions************************************/
  container bras-dot1x-access {
    description
      "Dot1x access.";
    container dot1x-templates {
      description
        "List of dot1x templates. Has default record dot1x-template index 1.";
      list dot1x-template {
        key "index";
        max-elements "256";
        description
          "Configure dot1x template.";
        ext:generated-by system {
          ext:filter "index=1";
          description "The instance whose index is 1 is generated by system automatically.";
        }
        ext:operation-exclude create|delete {
          ext:filter "index=1";
          description "The instance whose index is 1 cannot be created or deleted.";
        }
        leaf index {
          type uint16 {
            range "1..256";
          }
          description
            "Dot1x template index.";
        }
        leaf re-authentication-interval {
          type uint32 {
            range "0..65535";
          }
          default "57600";
          description
            "Re-authentication interval time.";
        }
        leaf authentication-timeout {
          type uint16 {
            range "1..300";
          }
          units s;
          default "30";
          description
            "Authentication timeout interval.";
        }
        leaf authentication-method {
          type enumeration {
            enum "chap" {
              value 0;
              description
                "CHAP encryption.";
            }
            enum "pap" {
              value 1;
              description
                "PAP encryption.";
            }
            enum "none" {
              value 2;
              description
                "EAP relay mode.";
            }
          }
          default "none";
          description
            "Dot1x authentication method.";
        }
        leaf keepalive-interval {
          type uint16 {
            range "1..1800";
          }
          default "20";
          description
            "KeepAlive interval.";
        }
        leaf keepalive-retransmit {
          type uint16 {
            range "0..10";
          }
          default "0";
          description
            "Number of KeepAlive retransmission times.";
        }
        leaf request-interval {
          type uint16 {
            range "1..300";
          }
          default "30";
          description
            "Interval for sending request packets.";
        }
        leaf request-retransmit {
          type uint16 {
            range "1..10";
          }
          default "2";
          description
            "Number of request retransmission times.";
        }
      }
    }
    container dot1x-sessions {
      config false;
      description
        "List of information about 802.1X sessions.";
      list dot1x-session {
        key "user-index";
        description
          "Statistics of 802.1X sessions information.";
        leaf user-index {
          type uint32;
          description
            "EAP user index.";
        }
        leaf slot-id {
          type string {
            length "1..15";
          }
          description
            "Specify the slot ID of an installed board based on which information about 802.1X sessions is to be displayed.";
          ext:support-filter "true";
        }
        leaf mac-address {
          type pub-type:mac-address;
          description
            "User MAC address.";
          ext:support-filter "true";
        }
        leaf interface {
          type string {
            length "1..49";
          }
          description
            "Specify the interface name.";
          ext:support-filter "true";
        }
        leaf user-state {
          type dot1x-user-state;
        description
          "Current EAPoL state machine status of a user.";
        }
        leaf vlan-id {
          type uint32;
          description
            "User VLAN ID.";
        }
        leaf qinq-id {
          type uint32;
          description
            "Inner VLAN ID or outer VLAN ID of a QinQ interface.";
        }
        leaf mac-bypass-vlan {
          type uint16;
          description
            "Whether VLAN information carried in the upstream traffic of the MAC address bypass authentication user is replaced by the configured VLAN.";
        }
      }
    }
    container dot1x-online-infos {
      config false;
      description
        "List of 802.1X sessions online information.";
      list dot1x-online-info {
        key "slot-id";
        description
          "Statistics of 802.1X sessions online information.";
        leaf slot-id {
          type string {
            length "1..15";
          }
          description
            "Specify the slot ID of an installed board based on which information about 802.1X sessions is to be displayed.";
        }
        leaf user-online-num {
          type uint32;
          description
            "User online number.";
        }
      }
    }
    container dot1x-interfaces {
      config false;
      description
        "List of information about 802.1X authentication on an interface.";
      list dot1x-interface {
        key "interface";
        description
          "Statistics of 802.1X authentication information on an interface.";
        leaf interface {
          type string {
            length "1..49";
          }
          description
            "Specify the interface name.";
        }
        leaf port-current-status {
          type port-current-state;
          description
            "Current authorization status of an interface.";
        }
        leaf port-access-user-num {
          type uint32;
          description
            "Current number of access users on an interface.";
        }
      }
    }
    container dot1x-statistics {
      config false;
      description
        "List of information about 802.1X authentication on an interface.";
      list dot1x-statistic {
        key "slot-id";
        description
          "Statistics of 802.1X authentication information on an interface.";
        leaf slot-id {
          type string {
            length "1..15";
          }
          description
            "Specify the slot ID of an interface board based on which 802.1X statistics are displayed.";
        }
        leaf eap-request-identity {
          type uint32;
          description
            "Total number of EAP-Request/Identity packets sent to terminals.";
        }
        leaf eap-response-identity {
          type uint32;
          description
            "Total number of received EAP-Response/Identity packets.";
        }
        leaf eap-request-sim-challenge {
          type uint32;
          description
            "Total number of EAP-Request/SIM/Challenge packets sent to terminals.";
        }
        leaf eap-response-sim-challenge {
          type uint32;
          description
            "Total number of received EAP-Response/SIM/Challenge packets.";
        }
        leaf eap-request-tls {
          type uint32;
          description
            "Total number of received EAP-Request/TLS packets.";
        }
        leaf eap-response-tls {
          type uint32;
          description
            "Total number of received EAP-Response/TLS packets.";
        }
        leaf eap-success {
          type uint32;
          description
            "Total number of EAP-Success packets sent to terminals.";
        }
        leaf eap-failure {
          type uint32;
          description
            "Total number of EAP-Failure packets sent to terminals.";
        }
        leaf eapol-start {
          type uint32;
          description
            "Total number of received EAPOL-Start packets.";
        }
        leaf eapol-logoff {
          type uint32;
          description
            "Total number of received EAPOL-Logoff packets.";
        }
        leaf eapol-key {
          type uint32;
          description
            "Total number of received EAPOL-Key packets.";
        }
        leaf eap-limit-drop {
          type uint32;
          description
            "Total number of discarded Start packets when the number of users exceeds the upper limit.";
        }
      }
    }
  }

  /*****************************************************************
  * rpc 
  *****************************************************************/
    rpc reset-dot1x-statistic {
      description
        "Clear 802.1X statistics.";
      ext:node-ref "/bras-dot1x-access:bras-dot1x-access/bras-dot1x-access:dot1x-statistics/bras-dot1x-access:dot1x-statistic";
      input {
        leaf slot-id {
          type string {
            length "1..15";
          }
          mandatory true;
          description
            "Specify the slot number of an interface board based on which 802.1X statistics are cleared.";
        }
      }
    }

  augment "/ifm:ifm/ifm:interfaces/ifm:interface/bras-basic-access:bas/bras-basic-access:access-type/bras-basic-access:layer2-subscriber/bras-basic-access:layer2-subscriber" {
    description
      "Configure the device to initiate EAP authentication.";
    container dot1x-trigger {
      leaf trigger-enable {
        type empty;
        description
          "Whether to enable the device to initiate EAP authentication.";
      }
      description
        "Configure the device to initiate EAP authentication. By default, the device is disabled from initiating EAP authentication.";
    }
  }
}
