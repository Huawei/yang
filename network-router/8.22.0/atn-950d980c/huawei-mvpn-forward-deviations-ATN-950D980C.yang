/*
Copyright (C) 2021 Huawei Technologies Co., Ltd. All rights reserved.
*/
module huawei-mvpn-forward-deviations-ATN-950D980C {
  namespace "urn:huawei:yang:huawei-mvpn-forward-deviations-ATN-950D980C";
  prefix mvpn-forward-devs-ATN-950D980C;

  import huawei-mvpn-forward {
    prefix mvpn-forward;
  }

  organization
    "Huawei Technologies Co., Ltd.";

  contact
    "Huawei Industrial Base
     Bantian, Longgang
     Shenzhen 518129
     People's Republic of China
     Website: http://www.huawei.com
     Email: support@huawei.com";

  description
    "This module defines deviation statements for huawei-mvpn-forward module.";

  revision 2021-05-07 {
    description
      "Initial revision.";
    reference
      "Huawei private.";
  }

  deviation "/mvpn-forward:mvpn-forward/mvpn-forward:global/mvpn-forward:multicast-vpn-slots" {
    deviate not-supported;
  }

}
