/*
Copyright (C) 2021 Huawei Technologies Co., Ltd. All rights reserved.
*/
module huawei-qppb-deviations-ATN-950D980C {
  namespace "urn:huawei:yang:huawei-qppb-deviations-ATN-950D980C";
  prefix qppb-devs-ATN-950D980C;

  import huawei-qppb {
    prefix qppb;
  }

  import huawei-ifm {
    prefix ifm;
  }

  import huawei-qos {
    prefix qos;
  }

  organization
    "Huawei Technologies Co., Ltd.";

  contact
    "Huawei Industrial Base
     Bantian, Longgang
     Shenzhen 518129
     People's Republic of China
     Website: http://www.huawei.com
     Email: support@huawei.com";

  description
    "This module defines deviation statements for huawei-qppb module.";

  revision 2021-05-07 {
    description
      "Initial revision.";
    reference
      "Huawei private.";
  }

  deviation "/qos:qos/qos:global-config/qppb:local-id-enable" {
    deviate not-supported;
  }
  deviation "/ifm:ifm/ifm:interfaces/ifm:interface/qos:qos/qppb:local-id-enable/qppb:both" {
    deviate not-supported;
  }

}
