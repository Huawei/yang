/*
Copyright (C) 2021 Huawei Technologies Co., Ltd. All rights reserved.
*/
module huawei-clocksync-notification-deviations-ATN-950D980C {
  namespace "urn:huawei:yang:huawei-clocksync-notification-deviations-ATN-950D980C";
  prefix clocksync-notification-devs-ATN-950D980C;

  import huawei-clocksync-notification {
    prefix clocksync-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-clocksync-notification module.";

  revision 2021-05-07 {
    description
      "Initial revision.";
    reference
      "Huawei private.";
  }

  deviation "/clocksync-notification:clock-cluster-topo-fail" {
    deviate not-supported;
  }
  deviation "/clocksync-notification:clock-cluster-topo-fail-resume" {
    deviate not-supported;
  }
  deviation "/clocksync-notification:ptp-acr-sync-bad" {
    deviate not-supported;
  }
  deviation "/clocksync-notification:ptp-acr-sync-bad-resume" {
    deviate not-supported;
  }

}
