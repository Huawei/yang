/*
Copyright (C) 2021 Huawei Technologies Co., Ltd. All rights reserved.
*/
module huawei-ssl-deviations-ATN-950D980C {
  namespace "urn:huawei:yang:huawei-ssl-deviations-ATN-950D980C";
  prefix ssl-devs-ATN-950D980C;

  import huawei-ssl {
    prefix ssl;
  }

  organization
    "Huawei Technologies Co., Ltd.";
  contact
    "Huawei Industrial Base
     Bantian, Longgang
     Shenzhen 518129
     People's Republic of China
     Website: http://www.huawei.com
     Email: support@huawei.com";
  description
    "This module defines deviation statements for huawei-ssl module.";

  revision 2021-05-07 {
    description
      "Initial revision.";
    reference "Huawei private.";
  }

  deviation "/ssl:ssl/ssl:ssl-policys/ssl:ssl-policy/ssl:ecdh-group" {
    deviate not-supported;
  }
  deviation "/ssl:ssl/ssl:ssl-policys/ssl:ssl-policy/ssl:cert-loads/ssl:cert-load/ssl:is-cert-file-encrypted" {
    deviate not-supported;
  }
}
