/*
Copyright (C) 2021 Huawei Technologies Co., Ltd. All rights reserved.
*/
module huawei-openconfig-system-deviations-ATN-950D980C {
  namespace "urn:huawei:yang:huawei-openconfig-system-deviations-ATN-950D980C";
  prefix oc-sys-devs-ATN-950D980C;

  import openconfig-system {
    prefix oc-sys;
  }
  import huawei-extension {
    prefix ext;
  }
  import openconfig-types {
    prefix oc-types;
  }
  import openconfig-inet-types {
    prefix oc-inet;
  }
  import openconfig-aaa-types {
    prefix oc-aaa-types;
  }

  organization
    "Huawei Technologies Co., Ltd.";
  contact
    "Huawei Industrial Base
     Bantian, Longgang
     Shenzhen 518129
     People's Republic of China
     Website: http://www.huawei.com
     Email: support@huawei.com";
  description
    "This module defines deviation statements for openconfig-system module.";

  revision 2021-05-07 {
    description
      "Initial revision.";
    reference "Huawei private.";
  }

  deviation "/oc-sys:system/oc-sys:config/oc-sys:domain-name" {
    deviate not-supported;
  }
  deviation "/oc-sys:system/oc-sys:config/oc-sys:login-banner" {
    deviate not-supported;
  }
  deviation "/oc-sys:system/oc-sys:config/oc-sys:motd-banner" {
    deviate not-supported;
  }
  deviation "/oc-sys:system/oc-sys:state" {
    deviate not-supported;
  }
  deviation "/oc-sys:system/oc-sys:mount-points" {
    deviate not-supported;
  }
  deviation "/oc-sys:system/oc-sys:clock" {
    deviate not-supported;
  }
  deviation "/oc-sys:system/oc-sys:dns/oc-sys:servers/oc-sys:server/oc-sys:config/oc-sys:port" {
    deviate not-supported;
  }
  deviation "/oc-sys:system/oc-sys:dns/oc-sys:servers/oc-sys:server/oc-sys:state/oc-sys:port" {
    deviate not-supported;
  }
  deviation "/oc-sys:system/oc-sys:dns/oc-sys:host-entries/oc-sys:host-entry/oc-sys:config/oc-sys:alias" {
    deviate not-supported;
  }
  deviation "/oc-sys:system/oc-sys:dns/oc-sys:host-entries/oc-sys:host-entry/oc-sys:state/oc-sys:alias" {
    deviate not-supported;
  }
  deviation "/oc-sys:system/oc-sys:ntp/oc-sys:config" {
    deviate not-supported;
  }
  deviation "/oc-sys:system/oc-sys:ntp/oc-sys:state" {
    deviate not-supported;
  }
  deviation "/oc-sys:system/oc-sys:ntp/oc-sys:ntp-keys" {
    deviate not-supported;
  }
  deviation "/oc-sys:system/oc-sys:ssh-server" {
    deviate not-supported;
  }
  deviation "/oc-sys:system/oc-sys:telnet-server" {
    deviate not-supported;
  }
  deviation "/oc-sys:system/oc-sys:logging/oc-sys:console" {
    deviate not-supported;
  }
  deviation "/oc-sys:system/oc-sys:logging/oc-sys:remote-servers/oc-sys:remote-server/oc-sys:state" {
    deviate not-supported;
  }
  deviation "/oc-sys:system/oc-sys:logging/oc-sys:remote-servers/oc-sys:remote-server/oc-sys:selectors" {
    deviate not-supported;
  }
  deviation "/oc-sys:system/oc-sys:aaa/oc-sys:config" {
    deviate not-supported;
  }
  deviation "/oc-sys:system/oc-sys:aaa/oc-sys:state" {
    deviate not-supported;
  }
  deviation "/oc-sys:system/oc-sys:aaa/oc-sys:authentication/oc-sys:state" {
    deviate not-supported;
  }
  deviation "/oc-sys:system/oc-sys:aaa/oc-sys:authentication/oc-sys:admin-user" {
    deviate not-supported;
  }
  deviation "/oc-sys:system/oc-sys:aaa/oc-sys:authentication/oc-sys:users/oc-sys:user/oc-sys:config/oc-sys:ssh-key" {
    deviate not-supported;
  }
  deviation "/oc-sys:system/oc-sys:aaa/oc-sys:authentication/oc-sys:users/oc-sys:user/oc-sys:state" {
    deviate not-supported;
  }
  deviation "/oc-sys:system/oc-sys:aaa/oc-sys:authorization/oc-sys:state" {
    deviate not-supported;
  }
  deviation "/oc-sys:system/oc-sys:aaa/oc-sys:authorization/oc-sys:events" {
    deviate not-supported;
  }
  deviation "/oc-sys:system/oc-sys:aaa/oc-sys:accounting/oc-sys:state" {
    deviate not-supported;
  }
  deviation "/oc-sys:system/oc-sys:aaa/oc-sys:accounting/oc-sys:events" {
    deviate not-supported;
  }
  deviation "/oc-sys:system/oc-sys:aaa/oc-sys:server-groups/oc-sys:server-group/oc-sys:state" {
    deviate not-supported;
  }
  deviation "/oc-sys:system/oc-sys:aaa/oc-sys:server-groups/oc-sys:server-group/oc-sys:servers/oc-sys:server/oc-sys:config/oc-sys:name" {
    deviate not-supported;
  }
  deviation "/oc-sys:system/oc-sys:aaa/oc-sys:server-groups/oc-sys:server-group/oc-sys:servers/oc-sys:server/oc-sys:state" {
    deviate not-supported;
  }
  deviation "/oc-sys:system/oc-sys:aaa/oc-sys:server-groups/oc-sys:server-group/oc-sys:servers/oc-sys:server/oc-sys:tacacs/oc-sys:state" {
    deviate not-supported;
  }
  deviation "/oc-sys:system/oc-sys:aaa/oc-sys:server-groups/oc-sys:server-group/oc-sys:servers/oc-sys:server/oc-sys:radius/oc-sys:state" {
    deviate not-supported;
  }
  deviation "/oc-sys:system/oc-sys:memory" {
    deviate not-supported;
  }
  deviation "/oc-sys:system/oc-sys:cpus" {
    deviate not-supported;
  }
  deviation "/oc-sys:system/oc-sys:processes" {
    deviate not-supported;
  }
  deviation "/oc-sys:system/oc-sys:alarms" {
    deviate not-supported;
  }
  deviation "/oc-sys:system/oc-sys:messages" {
    deviate not-supported;
  }
  deviation "/oc-sys:system/oc-sys:license" {
    deviate not-supported;
  }
  deviation "/oc-sys:system/oc-sys:config/oc-sys:hostname" {
    deviate replace {
      type string {
        length "1..246";
      }
    }
    deviate add {
      default "HUAWEI";
    }
  }
  deviation "/oc-sys:system/oc-sys:dns/oc-sys:host-entries/oc-sys:host-entry" {
    deviate add {
      must '(count(/oc-sys:system/oc-sys:dns/oc-sys:host-entries/oc-sys:host-entry) > 0 and ((/oc-sys:system/oc-sys:dns/oc-sys:host-entries/oc-sys:host-entry/oc-sys:config/oc-sys:ipv4-address) or (/oc-sys:system/oc-sys:dns/oc-sys:host-entries/oc-sys:host-entry/oc-sys:config/oc-sys:ipv6-address))) or (count(/oc-sys:system/oc-sys:dns/oc-sys:host-entries/oc-sys:host-entry) = 0)';
    }
  }
  deviation "/oc-sys:system/oc-sys:dns/oc-sys:host-entries/oc-sys:host-entry/oc-sys:config/oc-sys:hostname" {
    deviate replace {
      type string {
        length "1..255";
      }
    }
  }
  deviation "/oc-sys:system/oc-sys:dns/oc-sys:host-entries/oc-sys:host-entry/oc-sys:state/oc-sys:hostname" {
    deviate replace {
      type string {
        length "1..255";
      }
    }
  }
  deviation "/oc-sys:system/oc-sys:ntp/oc-sys:servers/oc-sys:server/oc-sys:config/oc-sys:port" {
    deviate replace {
      type oc-inet:port-number {
        range "123|1025..65535";
      }
    }
  }
  deviation "/oc-sys:system/oc-sys:ntp/oc-sys:servers/oc-sys:server/oc-sys:config/oc-sys:version" {
    deviate replace {
      default "3";
    }
  }
  deviation "/oc-sys:system/oc-sys:ntp/oc-sys:servers/oc-sys:server/oc-sys:config/oc-sys:association-type" {
    deviate replace {
      type enumeration {
        enum SERVER {
          value 2;
          description
            "Use client association mode. This device
             will not provide synchronization to the
             configured NTP server.";
        }
        enum PEER {
          value 1;
          description
            "Use symmetric active association mode.
             This device may provide synchronization
             to the configured NTP server.";
        }
      }
    }
  }
  deviation "/oc-sys:system/oc-sys:ntp/oc-sys:servers/oc-sys:server/oc-sys:state/oc-sys:port" {
    deviate replace {
      type oc-inet:port-number {
        range "123|1025..65535";
      }
    }
  }
  deviation "/oc-sys:system/oc-sys:ntp/oc-sys:servers/oc-sys:server/oc-sys:state/oc-sys:version" {
    deviate replace {
      default "3";
    }
  }
  deviation "/oc-sys:system/oc-sys:ntp/oc-sys:servers/oc-sys:server/oc-sys:state/oc-sys:association-type" {
    deviate replace {
      type enumeration {
        enum SERVER {
          value 2;
          description
            "Use client association mode. This device
             will not provide synchronization to the
             configured NTP server.";
        }
        enum PEER {
          value 1;
          description
            "Use symmetric active association mode.
             This device may provide synchronization
             to the configured NTP server.";
        }
      }
    }
  }
  deviation "/oc-sys:system/oc-sys:aaa/oc-sys:authentication/oc-sys:users/oc-sys:user/oc-sys:config/oc-sys:role" {
    deviate replace {
      type union {
        type string {
          length "1..32";
        }
        type identityref {
          base oc-aaa-types:SYSTEM_DEFINED_ROLES;
        }
      }
    }
  }
  deviation "/oc-sys:system/oc-sys:aaa/oc-sys:server-groups/oc-sys:server-group/oc-sys:config/oc-sys:name" {
    deviate replace {
      type string {
        length "1..32";
        pattern '[a-z0-9._-]+';
      }
    }
  }
  deviation "/oc-sys:system/oc-sys:aaa/oc-sys:server-groups/oc-sys:server-group/oc-sys:config/oc-sys:type" {
    deviate add {
      mandatory true;
    }
  }
  deviation "/oc-sys:system/oc-sys:aaa/oc-sys:server-groups/oc-sys:server-group/oc-sys:servers/oc-sys:server/oc-sys:config/oc-sys:timeout" {
    deviate replace {
      type uint16 {
        range "3..25";
      }
    }
  }
  deviation "/oc-sys:system/oc-sys:aaa/oc-sys:server-groups/oc-sys:server-group/oc-sys:servers/oc-sys:server/oc-sys:tacacs/oc-sys:config/oc-sys:port" {
    deviate replace {
      type oc-inet:port-number {
        range "1..65535";
      }
    }
  }
  deviation "/oc-sys:system/oc-sys:aaa/oc-sys:server-groups/oc-sys:server-group/oc-sys:servers/oc-sys:server/oc-sys:tacacs/oc-sys:config/oc-sys:secret-key" {
    deviate replace {
      type oc-types:routing-password {
        length "1..128";
      }
    }
  }
  deviation "/oc-sys:system/oc-sys:aaa/oc-sys:server-groups/oc-sys:server-group/oc-sys:servers/oc-sys:server/oc-sys:tacacs/oc-sys:config/oc-sys:secret-key-hashed" {
    deviate replace {
      type oc-aaa-types:crypt-password-type {
        length "1..268";
      }
    }
  }
  deviation "/oc-sys:system/oc-sys:aaa/oc-sys:server-groups/oc-sys:server-group/oc-sys:servers/oc-sys:server/oc-sys:radius/oc-sys:config/oc-sys:auth-port" {
    deviate replace {
      type oc-inet:port-number {
        range "1..65535";
      }
    }
  }
  deviation "/oc-sys:system/oc-sys:aaa/oc-sys:server-groups/oc-sys:server-group/oc-sys:servers/oc-sys:server/oc-sys:radius/oc-sys:config/oc-sys:acct-port" {
    deviate replace {
      type oc-inet:port-number {
        range "1..65535";
      }
    }
  }
  deviation "/oc-sys:system/oc-sys:aaa/oc-sys:server-groups/oc-sys:server-group/oc-sys:servers/oc-sys:server/oc-sys:radius/oc-sys:config/oc-sys:secret-key" {
    deviate replace {
      type oc-types:routing-password {
        length "1..128";
      }
    }
  }
  deviation "/oc-sys:system/oc-sys:aaa/oc-sys:server-groups/oc-sys:server-group/oc-sys:servers/oc-sys:server/oc-sys:radius/oc-sys:config/oc-sys:secret-key-hashed" {
    deviate replace {
      type oc-aaa-types:crypt-password-type {
        length "1..268";
      }
    }
  }
  deviation "/oc-sys:system/oc-sys:aaa/oc-sys:server-groups/oc-sys:server-group/oc-sys:servers/oc-sys:server/oc-sys:radius/oc-sys:config/oc-sys:retransmit-attempts" {
    deviate replace {
      type uint8 {
        range "1..5";
      }
    }
  }
  ext:deviation-ext "/oc-sys:system/oc-sys:aaa/oc-sys:server-groups/oc-sys:server-group/oc-sys:config/oc-sys:name" {
    ext:deviate-ext "add" {
      ext:case-sensitivity "lower-only";
    }
  }
}
