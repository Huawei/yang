/*
Copyright (C) 2021 Huawei Technologies Co., Ltd. All rights reserved.
*/
module huawei-evpl-ext-deviations-ATN-950D980C {
  namespace "urn:huawei:yang:huawei-evpl-ext-deviations-ATN-950D980C";
  prefix evpl-ext-devs-ATN-950D980C;

  import huawei-evpl-ext {
    prefix evpl-ext;
  }

  import huawei-evpl {
    prefix evpl;
  }

  organization
    "Huawei Technologies Co., Ltd.";

  contact
    "Huawei Industrial Base
     Bantian, Longgang
     Shenzhen 518129
     People's Republic of China
     Website: http://www.huawei.com
     Email: support@huawei.com";

  description
    "This module defines deviation statements for huawei-evpl-ext module.";

  revision 2021-05-07 {
    description
      "Initial revision.";
    reference
      "Huawei private.";
  }

  deviation "/evpl:evpl/evpl:instances/evpl:instance/evpl-ext:pipe/evpl-ext:color" {
    deviate not-supported;
  }

}
