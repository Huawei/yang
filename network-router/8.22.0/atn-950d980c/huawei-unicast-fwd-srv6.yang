/*
Copyright (C) 2020-2022 Huawei Technologies Co., Ltd. All rights reserved.
*/
module huawei-unicast-fwd-srv6 {
  yang-version 1;
  namespace "urn:huawei:yang:huawei-unicast-fwd-srv6";
  prefix unicast-fwd-srv6;
  import huawei-network-instance {
    prefix ni;
  }
  import huawei-extension {
    prefix ext;
  }
   import huawei-srv6 {
    prefix srv6;
  }
  import huawei-license {
    prefix lcs;
  }
  import huawei-devm {
    prefix devm;
  }
  import huawei-qos {
    prefix qos;
  }
  import huawei-ifm {
    prefix ifm;
  }
  import huawei-net-slice {
    prefix net-slice;
  }
  organization
    "Huawei Technologies Co., Ltd.";
  contact
    "Huawei Industrial Base
    Bantian, Longgang
    Shenzhen 518129
    People's Republic of China
    Website: http://www.huawei.com
    Email: support@huawei.com";
  description
    "Unicast forward SRv6 configuration.";
  revision 2022-04-16 {
    description
      "Add remark-network-slice node.";
    reference
      "Huawei private.";
  }
  revision 2020-03-19 {
    description
      "Initial revision.";
    reference
      "Huawei private.";
  }
  typedef srv6-ttl-mode-type {
    type enumeration {
      enum "pipe" {
        value 1;
        description
          "Pipe mode.";
      }
      enum "uniform" {
        value 3;
        description
          "Uniform mode.";
      }
    }
    description
      "SRv6 TTL mode type.";
  }
  typedef lcs-slice-rtu-type {
    type enumeration {
      enum "data-plane" {
        value 1;
        description
          "License type for data-plane.";
      }
      enum "flex-channel" {
        value 2;
        description
          "License type for flex-channel.";
      }
    }
    description
      "Network-slice license type.";
  }
   typedef flex-chan-service-class {
    type enumeration {
      enum "be" {
        value 0; 
        description
          "BE service-class.";
      }
      enum "af1" {
        value 1; 
        description
          "AF1 service-class.";
      }
      enum "af2" {
        value 2; 
        description
          "AF2 service-class.";
      }
      enum "af3" {
        value 3; 
        description
          "AF3 service-class.";
      }
      enum "af4" {
        value 4; 
        description
          "AF4 service-class.";
      }
      enum "ef" {
        value 5; 
        description
          "EF service-class.";
      }
      enum "cs6" {
        value 6; 
        description
          "CS6 service-class.";
      }
      enum "cs7" {
        value 7; 
        description
          "CS7 service-class.";
      }
    }
    description
      "Queue type.";
  }
  ext:task-name "forwarding";
  rpc reset-flex-channel-statistics {
    description
      "Reset flex-channel statistics.";
    ext:node-ref "/ifm:ifm/ifm:interfaces/ifm:interface/net-slice:net-slices/net-slice:net-slice/unicast-fwd-srv6:flex-channel-statisticss";
    input {
      leaf slice-id {
        type uint32 {
        range "1 .. 4294967295";
        }
        description
          "Net-slice instance.";
      }
      leaf interface-name {
        type leafref {
            path "/ifm:ifm/ifm:interfaces/ifm:interface/ifm:name";
        }
        description
          "Interface name.";
      }
    }
  }
  augment "/ni:network-instance/ni:instances/ni:instance/srv6:srv6" {
    description
      "Unicast forward configuration to the SRv6 module.";
    container global-ipv6uc-attribute {
      when "../srv6:enable = 'true'";
      description
        "Configure global IPv6 unicast attributes.";
      leaf forward-mode-through {
        type boolean;
        default "false";
        description
          "Enable/disable the forwarding mode of an SRv6 Tunnel to software loopback.";
      }
      leaf srv6-ttl-mode{
        type srv6-ttl-mode-type;
        default "pipe";
        description
          "Set SRv6 tunnel-encapsulated mode.";
      }
    }
  }

  augment "/lcs:license" {
    description
      "Network slice license.";
    container lcs-network-slices {
      description
        "List of license information about all boards network-slice resources.";
      list lcs-network-slice {
        key "slot-id license-type";
        description
          "Configure license information about a board to active network-slice resources.";
        leaf slot-id {
          type leafref {
            path "/devm:devm/devm:lpu-boards/devm:lpu-board/devm:position";
          }
          description
            "Indicates the slot ID of a board.";
        }
        leaf license-type {
          type lcs-slice-rtu-type;
            description
              "Network slice license type.";
        }
        leaf resource-size {
          type uint32 {
            range "1..65535";
          }
          mandatory true;
          description
            "The number of network-slice resources is related to a specific board.";
        }
      }
    }
    container lcs-usage-slice-items {
      config false;
      description
        "List of network slice license resource usage information.";
      list lcs-usage-slice-item {
        key "feature-name";
        description
          "Statistics of network slice license resource usage information.";
        leaf feature-name {
          type string {
            length "1..31";
          }
          description
            "Name of the control item corresponding to the network license.";
        }
        leaf feature-description {
          type string {
            length "1..255";
          }
          description
            "Description of the control item corresponding to the network license.";
        }
        leaf activated-total {
          type uint32;
          description
            "Number of activated resources.";
        }
        leaf available-total {
          type uint32;
          description
            "Number of remaining available resources.";
        }
        leaf total {
          type uint32;
          description
            "Total number of resources.";
        }
        container lcs-info-boards {
        description
          "List of board network slice license information.";
          list lcs-info-board {
            key "position";
            description
              "Statistics of network slice license usage information on a board.";
            leaf position {
              type string {
                length "1..32";
              }
              description
                "Board position.";
            }
            leaf barcode {
              type string {
                length "1..128";
              }
              description
                "Bar code in the electronic label of a board.";
            }
            leaf usage-on-board {
              type uint32;
              description
              "Number of used resources on a board.";
            }
            leaf available-on-board {
              type uint32;
              description
                "Number of remaining available resources on a board.";
            }
            leaf activated-on-board {
              type uint32;
              description
                "Total number of resources on a board.";
            }
          }
        }
      }
    }
  }
  augment "/qos:qos/qos:classifier-template/qos:traffic-behaviors/qos:traffic-behavior" {
    description
      "Unicast forward configuration to the traffic-behavior module.";
    container unicast-fwd-srv6 {
      description
        "Configure traffic behavior.";
      container remark-te-class {
        description
          "Configure te-class ID.";
        leaf te-class-id {
          type uint16 {
              range "1..65535";
            }
          description
            "Set te-class ID.";
        }
      }
      container remark-network-slice {
        description
          "Configure network-slice ID.";
        leaf network-slice-id {
          type leafref {
            path "/net-slice:net-slice/net-slice:instances/net-slice:instance/net-slice:id";
          }
          must "../network-slice-id!=0";
          description
            "Set network-slice ID.";
        }
      }
    }
  }
  augment "/ifm:ifm/ifm:interfaces/ifm:interface/net-slice:net-slices/net-slice:net-slice" {
    description
      "Unicast forward configuration to the net-slice module.";
    container flex-channel-statisticss {
      config false;
      description
        "List of flex-channel statistics.";
      list flex-channel-statistics {
        key "service-class";
        description
        "Statistics of flex-channel.";
        leaf service-class {
          type flex-chan-service-class;
          description
            "Class of service.";
        }
        leaf passed-packets {
          type uint64;
          units "packet";
          description
            "Passed packets.";
        }
        leaf passed-bytes {
          type uint64;
          units "Byte";
          description
            "Passed bytes.";
        }
        leaf dropped-packets {
          type uint64;
          units "packet";
          description
            "Dropped packets.";
        }
        leaf dropped-bytes {
          type uint64;
          units "Byte";
          description
            "Dropped bytes.";
        }
        leaf passed-pps {
          type uint64;
          units "pps";
          description
            "Passed pps.";
        }
        leaf passed-bps {
          type uint64;
          units "bit/s";
          description
            "Passed bps.";
        }
        leaf dropped-pps {
          type uint64;
          units "pps";
          description
            "Dropped pps.";
        }
        leaf dropped-bps {
          type uint64;
          units "bit/s";
          description
            "Dropped bps.";
        }
      }
    }
  }
}
