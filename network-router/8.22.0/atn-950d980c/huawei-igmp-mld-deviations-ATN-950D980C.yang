/*
Copyright (C) 2021 Huawei Technologies Co., Ltd. All rights reserved.
*/
module huawei-igmp-mld-deviations-ATN-950D980C {
  namespace "urn:huawei:yang:huawei-igmp-mld-deviations-ATN-950D980C";
  prefix igmp-mld-devs-ATN-950D980C;

  import huawei-igmp-mld {
    prefix igmp-mld;
  }
  import huawei-multicast {
    prefix mc;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-igmp-mld module.";

  revision 2021-05-07 {
    description
      "Initial revision.";
    reference "Huawei private.";
  }

  deviation "/mc:multicast/igmp-mld:igmp/igmp-mld:disable-dhcp-stb-packet-copys" {
    deviate not-supported;
  }
  deviation "/ni:network-instance/ni:instances/ni:instance/igmp-mld:igmp/igmp-mld:global/igmp-mld:query-response-interval" {
    deviate replace {
      type uint32 {
        range "1..25";
      }
    }
  }
  deviation "/ni:network-instance/ni:instances/ni:instance/igmp-mld:igmp/igmp-mld:global/igmp-mld:last-member-query-interval" {
    deviate replace {
      type uint32 {
        range "1..5";
      }
    }
  }
  deviation "/ni:network-instance/ni:instances/ni:instance/igmp-mld:igmp/igmp-mld:interfaces/igmp-mld:interface/igmp-mld:query-response-interval" {
    deviate replace {
      type uint32 {
        range "1..25";
      }
    }
  }
  deviation "/ni:network-instance/ni:instances/ni:instance/igmp-mld:igmp/igmp-mld:interfaces/igmp-mld:interface/igmp-mld:last-member-query-interval" {
    deviate replace {
      type uint32 {
        range "1..5";
      }
    }
  }
  deviation "/ni:network-instance/ni:instances/ni:instance/igmp-mld:mld/igmp-mld:global/igmp-mld:query-response-interval" {
    deviate replace {
      type uint32 {
        range "1..25";
      }
    }
  }
  deviation "/ni:network-instance/ni:instances/ni:instance/igmp-mld:mld/igmp-mld:global/igmp-mld:last-member-query-interval" {
    deviate replace {
      type uint32 {
        range "1..5";
      }
    }
  }
  deviation "/ni:network-instance/ni:instances/ni:instance/igmp-mld:mld/igmp-mld:interfaces/igmp-mld:interface/igmp-mld:query-response-interval" {
    deviate replace {
      type uint32 {
        range "1..25";
      }
    }
  }
  deviation "/ni:network-instance/ni:instances/ni:instance/igmp-mld:mld/igmp-mld:interfaces/igmp-mld:interface/igmp-mld:last-member-query-interval" {
    deviate replace {
      type uint32 {
        range "1..5";
      }
    }
  }
}
