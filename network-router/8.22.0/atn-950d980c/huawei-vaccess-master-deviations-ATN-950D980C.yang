/*
Copyright (C) 2021 Huawei Technologies Co., Ltd. All rights reserved.
*/
module huawei-vaccess-master-deviations-ATN-950D980C {
  namespace "urn:huawei:yang:huawei-vaccess-master-deviations-ATN-950D980C";
  prefix vaccess-master-devs-ATN-950D980C;

  import huawei-vaccess-master {
    prefix vaccess-master;
  }
  import huawei-network-instance {
    prefix ni;
  }
  import huawei-vaccess {
    prefix vaccess;
  }

  organization
    "Huawei Technologies Co., Ltd.";
  contact
    "Huawei Industrial Base
     Bantian, Longgang
     Shenzhen 518129
     People's Republic of China
     Website: http://www.huawei.com
     Email: support@huawei.com";
  description
    "This module defines deviation statements for huawei-vaccess-master module.";

  revision 2021-05-07 {
    description
      "Initial revision.";
    reference "Huawei private.";
  }

  deviation "/vaccess:vaccess/vaccess-master:master" {
    deviate not-supported;
  }
  deviation "/ni:network-instance/ni:instances/ni:instance/vaccess-master:vaccess-interfaces" {
    deviate not-supported;
  }
}
