/*
Copyright (C) 2021 Huawei Technologies Co., Ltd. All rights reserved.
*/
module huawei-eai-service-notification-deviations-ATN-950D980C {
  namespace "urn:huawei:yang:huawei-eai-service-notification-deviations-ATN-950D980C";
  prefix eai-service-notification-devs-ATN-950D980C;

  import huawei-eai-service-notification {
    prefix eai-service-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-eai-service-notification module.";

  revision 2021-05-07 {
    description
      "Initial revision.";
    reference
      "Huawei private.";
  }

  deviation "/eai-service-notification:anomaly-packet-loss" {
    deviate not-supported;
  }
  deviation "/eai-service-notification:anomaly-packet-loss-resume" {
    deviate not-supported;
  }

}
