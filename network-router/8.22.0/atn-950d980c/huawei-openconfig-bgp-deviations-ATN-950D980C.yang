/*
Copyright (C) 2021 Huawei Technologies Co., Ltd. All rights reserved.
*/
module huawei-openconfig-bgp-deviations-ATN-950D980C {
  namespace "urn:huawei:yang:huawei-openconfig-bgp-deviations-ATN-950D980C";
  prefix oc-bgp-devs-ATN-950D980C;

  import openconfig-bgp {
    prefix oc-bgp;
  }

  organization
    "Huawei Technologies Co., Ltd.";
  contact
    "Huawei Industrial Base
     Bantian, Longgang
     Shenzhen 518129
     People's Republic of China
     Website: http://www.huawei.com
     Email: support@huawei.com";
  description
    "This module defines deviation statements for openconfig-bgp module.";

  revision 2021-05-07 {
    description
      "Initial revision.";
    reference "Huawei private.";
  }

  deviation "/oc-bgp:bgp" {
    deviate not-supported;
  }
}
