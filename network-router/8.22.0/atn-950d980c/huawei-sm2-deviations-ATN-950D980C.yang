/*
Copyright (C) 2021 Huawei Technologies Co., Ltd. All rights reserved.
*/
module huawei-sm2-deviations-ATN-950D980C {
  namespace "urn:huawei:yang:huawei-sm2-deviations-ATN-950D980C";
  prefix sm2-devs-ATN-950D980C;

  import huawei-sm2 {
    prefix sm2;
  }

  organization
    "Huawei Technologies Co., Ltd.";
  contact
    "Huawei Industrial Base
     Bantian, Longgang
     Shenzhen 518129
     People's Republic of China
     Website: http://www.huawei.com
     Email: support@huawei.com";
  description
    "This module defines deviation statements for huawei-sm2 module.";

  revision 2021-05-07 {
    description
      "Initial revision.";
    reference "Huawei private.";
  }

  deviation "/sm2:sm2" {
    deviate not-supported;
  }
}
