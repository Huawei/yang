/*
Copyright (C) 2021 Huawei Technologies Co., Ltd. All rights reserved.
*/
module huawei-ifm-atm-deviations-ATN-950D980C {
  namespace "urn:huawei:yang:huawei-ifm-atm-deviations-ATN-950D980C";
  prefix ifm-atm-devs-ATN-950D980C;

  import huawei-ifm-atm {
    prefix ifm-atm;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-ifm-atm module.";

  revision 2021-05-07 {
    description
      "Initial revision.";
    reference "Huawei private.";
  }

  deviation "/ifm:ifm/ifm:interfaces/ifm:interface/ifm-atm:atm/ifm-atm:interface-priority" {
    deviate not-supported;
  }
  deviation "/ifm:ifm/ifm:interfaces/ifm:interface/ifm-atm:atm/ifm-atm:pvcs/ifm-atm:pvc/ifm-atm:encapsulation" {
    deviate not-supported;
  }
  deviation "/ifm:ifm/ifm:interfaces/ifm:interface/ifm-atm:atm/ifm-atm:pvcs/ifm-atm:pvc/ifm-atm:priority" {
    deviate not-supported;
  }
  deviation "/ifm:ifm/ifm:interfaces/ifm:interface/ifm-atm:atm/ifm-atm:pvcs/ifm-atm:pvc/ifm-atm:map-ip-statics" {
    deviate not-supported;
  }
  deviation "/ifm:ifm/ifm:interfaces/ifm:interface/ifm-atm:atm/ifm-atm:pvcs/ifm-atm:pvc/ifm-atm:inarp-map-ip" {
    deviate not-supported;
  }
  deviation "/ifm:ifm/ifm:interfaces/ifm:interface/ifm-atm:atm/ifm-atm:pvps/ifm-atm:pvp/ifm-atm:priority" {
    deviate not-supported;
  }
  deviation "/ifm:ifm/ifm:interfaces/ifm:interface/ifm-atm:atm/ifm-atm:pvcs/ifm-atm:pvc" {
    deviate delete {
      must 'count(map-ip-statics/map-ip-static) + count(inarp-map-ip/minutes)<=32';
    }
    deviate delete {
      must "not(encapsulation!='aal5snap' and inarp-map-ip/inarp-enable='enable')";
    }
  }
  deviation "/ifm:ifm/ifm:interfaces/ifm:interface/ifm-atm:atm/ifm-atm:pvcs/ifm-atm:pvc/ifm-atm:map-vci" {
    deviate add {
      must "(../../../../ifm:class='sub-interface')";
    }
  }
}
