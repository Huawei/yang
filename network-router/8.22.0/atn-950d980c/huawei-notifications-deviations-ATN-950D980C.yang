/*
Copyright (C) 2021 Huawei Technologies Co., Ltd. All rights reserved.
*/
module huawei-notifications-deviations-ATN-950D980C {
  namespace "urn:huawei:yang:huawei-notifications-deviations-ATN-950D980C";
  prefix ncEvent-devs-ATN-950D980C;

  import notifications {
    prefix ncEvent;
  }

  organization
    "Huawei Technologies Co., Ltd.";
  contact
    "Huawei Industrial Base
     Bantian, Longgang
     Shenzhen 518129
     People's Republic of China
     Website: http://www.huawei.com
     Email: support@huawei.com";
  description
    "This module defines deviation statements for notifications module.";

  revision 2021-05-07 {
    description
      "Initial revision.";
    reference "Huawei private.";
  }

  deviation "/ncEvent:notification" {
    deviate not-supported;
  }
}
