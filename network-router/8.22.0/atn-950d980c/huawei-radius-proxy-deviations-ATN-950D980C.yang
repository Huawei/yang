/*
Copyright (C) 2021 Huawei Technologies Co., Ltd. All rights reserved.
*/
module huawei-radius-proxy-deviations-ATN-950D980C {
  namespace "urn:huawei:yang:huawei-radius-proxy-deviations-ATN-950D980C";
  prefix radius-proxy-devs-ATN-950D980C;

  import huawei-radius-proxy {
    prefix radius-proxy;
  }

  organization
    "Huawei Technologies Co., Ltd.";

  contact
    "Huawei Industrial Base
     Bantian, Longgang
     Shenzhen 518129
     People's Republic of China
     Website: http://www.huawei.com
     Email: support@huawei.com";

  description
    "This module defines deviation statements for huawei-radius-proxy module.";

  revision 2021-05-07 {
    description
      "Initial revision.";
    reference
      "Huawei private.";
  }

  deviation "/radius-proxy:radius-proxy" {
    deviate not-supported;
  }

}
