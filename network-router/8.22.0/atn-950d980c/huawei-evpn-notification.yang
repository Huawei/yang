/*
Copyright (C) 2019-2022 Huawei Technologies Co., Ltd. All rights reserved.
*/
module huawei-evpn-notification {
  yang-version 1;
  namespace "urn:huawei:yang:huawei-evpn-notification";
  prefix evpn-notification;
  import ietf-inet-types {
    prefix inet;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of EVPN.";
  revision 2022-06-17 {
    description
      "Modified EVPN qualify BUM resource alarm notification.";
    reference
      "Huawei private.";
  }
  revision 2022-06-16 {
    description
      "Modify description for evpn-discard-route.";
    reference
      "Huawei private.";
  }
  revision 2022-05-30 {
    description
      "Added EVPN qualify BUM resource alarm notification.";
    reference
      "Huawei private.";
  }
  revision 2019-11-21 {
    description
      "Init revision.";
    reference
      "Huawei private.";
  }
  ext:task-name "evpnbgp";
  notification evpn-etree-mul-err {
    description
      "In an EVPN E-Tree scenario where a CE is dual-homed to PEs, the leaf attributes of the PEs' AC interfaces bound to the EVPN instance were different, causing a traffic loop.";
    leaf evpn-instance-name {
      type string {
          length "1..31";
        }
      description
        "EVPN instance name.";
    }
    leaf interface-name {
      type string {
          length "1..63";
        }
      description
        "Interface name.";
    }
  }
  notification evpn-srv6-modify-arg {
    description
      "The minimum length of the ARG is changed, split horizon function may fail temporarily.";
    leaf last-arg-len {
      type uint32;
      description
        "Last ARG length.";
    }
    leaf current-arg-len {
      type uint32;
      description
        "Current ARG length.";
    }
  }
  notification evpn-discard-route {
    description
      "The EVPN instance discards newly learned MAC, MAC/IP, IMET, and Ethernet A-D per-EVI routes.";
    leaf route-type {
      type string {
        length "1..11";
      }
      description
        "The MAC or MAC/IP route type.";
    }
  }
  notification evpn-ringid-conflict-alm {
    description
      "The number of peers with the same ring-id exceeded the limit.";
    leaf ring-id {
      type uint32;
      description
        "Ring ID configured for the ring network.";
    }
    leaf router-id {
      type inet:ipv4-address-no-zone;
      description
        "Router ID of the device on which a ring ID is configured.";
    }
  }
  notification evpn-ringid-conflict-alm-clear {
    description
      "The number of peers with the same ring-id unexceeded the limit.";
    leaf ring-id {
      type uint32;
      description
        "Ring ID configured for the ring network.";
    }
    leaf router-id {
      type inet:ipv4-address-no-zone;
      description
        "Router ID of the device on which a ring ID is configured.";
    }
  }
  notification evpn-qualify-bum-res-alm {
    description
      "The number of EVPN qualify BUM resources reached the upper limit.";
    leaf upper-limit {
      type uint32;
      description
        "Upper limit value of the EVPN qualify BUM resources.";
    }
  }
  notification evpn-qualify-bum-res-alm-clear {
    description
      "The number of EVPN qualify BUM resources returned to normal.";
    leaf upper-limit {
      type uint32;
      description
        "Upper limit value of the EVPN qualify BUM resources.";
    }
  }
}
