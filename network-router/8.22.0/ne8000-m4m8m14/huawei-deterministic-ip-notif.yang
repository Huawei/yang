/*
Copyright (C) 2022 Huawei Technologies Co., Ltd. All rights reserved.
*/
module huawei-deterministic-ip-notif {
  namespace "urn:huawei:yang:huawei-deterministic-ip-notif";
  prefix deterministic-ip-huawei-notif;

  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "Notification of Deterministic IP.";
  revision 2022-09-23 {
    description
      "Modify data type of threshold.";
    reference
      "Huawei private.";
  }
  revision 2022-02-20 {
    description
      "Initial revision.";
    reference
      "Huawei private.";
  }

  ext:task-name "qos";
  notification deterministic-ip-clock-unlock {
    description
      "Packet loss or disorder may occur in DIP networking traffic because the 1588 clock is not synchronized.";
    leaf board-id {
      type string {
        length "0..15";
      }
      description
        "Board ID.";
    }
  }
  notification deterministic-ip-clock-unlock-resume {
    description
      "The 1588 clock has been synchronized, and DIP networking traffic is forwarded normally.";
    leaf board-id {
      type string {
        length "0..15";
      }
      description
        "Board ID.";
    }
  }
  notification deterministic-ip-over-bandwidth-threshold {
    description
      "DIP networking traffic exceeds threshold of the interface bandwidth, packet loss occurs in DIP networking traffic.";
    leaf interface-name {
      type string {
        length "1..511";
      }
      description
        "Interface name.";
    }
    leaf threshold {
      type uint32 {
        range "1..100";
      }
      units "%";
      description
        "Threshold value.";
    }
  }
  notification deterministic-ip-over-bandwidth-threshold-resume {
    description
      "DIP networking traffic falls below threshold of the interface bandwidth, no packet loss occurs in DIP networking traffic.";
    leaf interface-name {
      type string {
        length "1..511";
      }
      description
        "Interface name.";
    }
    leaf threshold {
      type uint32 {
        range "1..100";
      }
      units "%";
      description
        "Threshold value.";
    }
  }
}
