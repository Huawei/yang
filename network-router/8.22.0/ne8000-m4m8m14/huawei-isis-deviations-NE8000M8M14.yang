/*
Copyright (C) 2021 Huawei Technologies Co., Ltd. All rights reserved.
*/
module huawei-isis-deviations-NE8000M8M14 {
  namespace "urn:huawei:yang:huawei-isis-deviations-NE8000M8M14";
  prefix isis-devs-NE8000M8M14;

  import huawei-isis {
    prefix isis;
  }
  import huawei-ifm {
    prefix ifm;
  }
  import huawei-mpls-ldp {
    prefix mpls-ldp;
  }
  import huawei-l3vpn {
    prefix l3vpn;
  }
  import huawei-mpls-te {
    prefix mpls-te;
  }
  import huawei-mpls {
    prefix mpls;
  }
  import huawei-network-instance {
    prefix ni;
  }
  import huawei-tunnel-management {
    prefix tnlm;
  }

  organization
    "Huawei Technologies Co., Ltd.";
  contact
    "Huawei Industrial Base
     Bantian, Longgang
     Shenzhen 518129
     People's Republic of China
     Website: http://www.huawei.com
     Email: support@huawei.com";
  description
    "This module defines deviation statements for huawei-isis module.";

  revision 2021-05-07 {
    description
      "Initial revision.";
    reference "Huawei private.";
  }

  deviation "/ni:network-instance/ni:instances/ni:instance/isis:isis/isis:sites/isis:site/isis:te-set-subtlv" {
    deviate not-supported;
  }
  deviation "/ni:network-instance/ni:instances/ni:instance/isis:isis/isis:sites/isis:site/isis:apply-link-cost" {
    deviate not-supported;
  }
  deviation "/ni:network-instance/ni:instances/ni:instance/isis:isis/isis:sites/isis:site/isis:afs/isis:af/isis:apply-qppb" {
    deviate not-supported;
  }
  deviation "/ni:network-instance/ni:instances/ni:instance/isis:isis/isis:sites/isis:site/isis:peers/isis:peer/isis:ipv6-adj-sid" {
    deviate not-supported;
  }
  deviation "/ni:network-instance/ni:instances/ni:instance/l3vpn:afs/l3vpn:af/isis:isis-import-rts/isis:isis-import-rt/isis:src-vrf" {
    deviate add {
      must "(../../../l3vpn:type='ipv4-unicast' and /ni:network-instance/ni:instances/ni:instance[ni:name=current()]/l3vpn:afs/l3vpn:af[l3vpn:type='ipv4-unicast'])";
    }
  }
  deviation "/ni:network-instance/ni:instances/ni:instance/isis:isis/isis:sites/isis:site/isis:circuits/isis:circuit/isis:silent-enable" {
    deviate add {
      must "../silent-enable='false' or not(/ifm:ifm/ifm:interfaces/ifm:interface[ifm:name=current()/../isis:name]/tnlm:tunnel-protocol/mpls-te:te-tunnel)";
    }
  }
  deviation "/ni:network-instance/ni:instances/ni:instance/isis:isis/isis:sites/isis:site/isis:afs/isis:af/isis:max-load-balancing" {
    deviate replace {
      type uint32 {
        range "1..64";
      }
    }
  }
  deviation "/ni:network-instance/ni:instances/ni:instance/isis:isis/isis:sites/isis:site/isis:afs/isis:af/isis:mpls-ldp-global/isis:auto-flag" {
    deviate add {
      must "../auto-flag='false' or (../../../../../../../ni:name='_public_' and /mpls:mpls/mpls-ldp:ldp/mpls-ldp:enable='true')";
    }
  }
  deviation "/ni:network-instance/ni:instances/ni:instance/isis:isis/isis:sites/isis:site/isis:afs/isis:af/isis:topologys/isis:topology/isis:max-load-balancing" {
    deviate replace {
      type uint32 {
        range "1..64";
      }
    }
  }
}
