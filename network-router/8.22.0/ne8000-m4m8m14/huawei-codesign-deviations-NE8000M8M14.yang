/*
Copyright (C) 2021 Huawei Technologies Co., Ltd. All rights reserved.
*/
module huawei-codesign-deviations-NE8000M8M14 {
  namespace "urn:huawei:yang:huawei-codesign-deviations-NE8000M8M14";
  prefix codesign-devs-NE8000M8M14;

  import huawei-codesign {
    prefix codesign;
  }

  organization
    "Huawei Technologies Co., Ltd.";
  contact
    "Huawei Industrial Base
     Bantian, Longgang
     Shenzhen 518129
     People's Republic of China
     Website: http://www.huawei.com
     Email: support@huawei.com";
  description
    "This module defines deviation statements for huawei-codesign module.";

  revision 2021-05-07 {
    description
      "Initial revision.";
    reference "Huawei private.";
  }

  deviation "/codesign:codesign/codesign:software-crls/codesign:software-crl/codesign:valid" {
    deviate not-supported;
  }
}
