/*
Copyright (C) 2021 Huawei Technologies Co., Ltd. All rights reserved.
*/
module huawei-ietf-network-deviations-NE8000M8M14 {
  namespace "urn:huawei:yang:huawei-ietf-network-deviations-NE8000M8M14";
  prefix nw-devs-NE8000M8M14;

  import ietf-network {
    prefix nw;
  }

  organization
    "Huawei Technologies Co., Ltd.";
  contact
    "Huawei Industrial Base
     Bantian, Longgang
     Shenzhen 518129
     People's Republic of China
     Website: http://www.huawei.com
     Email: support@huawei.com";
  description
    "This module defines deviation statements for ietf-network module.";

  revision 2021-05-07 {
    description
      "Initial revision.";
    reference "Huawei private.";
  }

  deviation "/nw:networks" {
    deviate not-supported;
  }
}
