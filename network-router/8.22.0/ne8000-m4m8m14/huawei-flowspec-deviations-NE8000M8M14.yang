/*
Copyright (C) 2021-2022 Huawei Technologies Co., Ltd. All rights reserved.
*/
module huawei-flowspec-deviations-NE8000M8M14 {
  namespace "urn:huawei:yang:huawei-flowspec-deviations-NE8000M8M14";
  prefix flowspec-devs-NE8000M8M14;

  import huawei-flowspec {
    prefix flowspec;
  }
  import huawei-network-instance {
    prefix ni;
  }
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "This module defines deviation statements for huawei-flowspec module.";

  revision 2022-09-16 {
    description
      "The deviations of the huawei-flowspec module were modified.";
    reference "Huawei private.";
  }
  revision 2021-05-07 {
    description
      "Initial revision.";
    reference "Huawei private.";
  }

  deviation "/flowspec:flowspec/flowspec:ipv6-family/flowspec:interface-group-statisticss" {
    deviate not-supported;
  }
  deviation "/ni:network-instance/ni:instances/ni:instance/flowspec:flowspec/flowspec:flow-routes/flowspec:flow-route/flowspec:condition/flowspec:origin-ass" {
    deviate not-supported;
  }
  deviation "/flowspec:flowspec/flowspec:interface-groups" {
    deviate not-supported;
  }
  deviation "/ni:network-instance/ni:instances/ni:instance/flowspec:flowspec/flowspec:flow-routes/flowspec:flow-route/flowspec:interface-groups" {
    deviate not-supported;
  }
  deviation "/flowspec:flowspec/flowspec:ipv4-family/flowspec:interface-group-statisticss" {
    deviate not-supported;
  }
  deviation "/flowspec:reset-flowspec-statistics/flowspec:input/flowspec:group-id" {
    deviate not-supported;
  }
  ext:deviation-ext "/flowspec:reset-flowspec-statistics" {
    ext:deviate-ext "delete" {
      ext:node-ref "/flowspec:flowspec/flowspec:ipv4-family/flowspec:interface-group-statisticss/flowspec:interface-group-statistics";
    }
  }
}
