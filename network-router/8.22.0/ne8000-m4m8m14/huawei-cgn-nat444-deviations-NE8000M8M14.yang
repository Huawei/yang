/*
Copyright (C) 2021 Huawei Technologies Co., Ltd. All rights reserved.
*/
module huawei-cgn-nat444-deviations-NE8000M8M14 {
  namespace "urn:huawei:yang:huawei-cgn-nat444-deviations-NE8000M8M14";
  prefix cgn-nat444-devs-NE8000M8M14;

  import huawei-cgn-nat444 {
    prefix cgn-nat444;
  }

  import huawei-vsm {
    prefix vsm;
  }

  organization
    "Huawei Technologies Co., Ltd.";

  contact
    "Huawei Industrial Base
     Bantian, Longgang
     Shenzhen 518129
     People's Republic of China
     Website: http://www.huawei.com
     Email: support@huawei.com";

  description
    "This module defines deviation statements for huawei-cgn-nat444 module.";

  revision 2021-05-07 {
    description
      "Initial revision.";
    reference
      "Huawei private.";
  }

  deviation "/cgn-nat444:cgn-nat444/cgn-nat444:nat-instances/cgn-nat444:nat-instance/cgn-nat444:log/cgn-nat444:send-mode" {
    deviate not-supported;
  }
  deviation "/cgn-nat444:cgn-nat444/cgn-nat444:nat-instances/cgn-nat444:nat-instance/cgn-nat444:port-range" {
    deviate add {
      must "/vsm:vsm/vsm:on-board-mode/vsm:mode='centralized-board'";
    }
  }
  deviation "/cgn-nat444:cgn-nat444/cgn-nat444:nat-instances/cgn-nat444:nat-instance/cgn-nat444:address-groups/cgn-nat444:address-group/cgn-nat444:address/cgn-nat444:bind-ip-pool/cgn-nat444:ip-pool" {
    deviate add {
      must "/vsm:vsm/vsm:on-board-mode/vsm:mode='centralized-board'";
    }
  }
  deviation "/cgn-nat444:cgn-nat444/cgn-nat444:nat-instances/cgn-nat444:nat-instance/cgn-nat444:nat-translate" {
    deviate add {
      must "/vsm:vsm/vsm:on-board-mode/vsm:mode='centralized-board'";
    }
  }
  deviation "/cgn-nat444:cgn-nat444/cgn-nat444:nat-instances/cgn-nat444:nat-instance/cgn-nat444:filter-mode" {
    deviate add {
      must "/vsm:vsm/vsm:on-board-mode/vsm:mode='centralized-board'";
    }
  }
  deviation "/cgn-nat444:cgn-nat444/cgn-nat444:nat-instances/cgn-nat444:nat-instance/cgn-nat444:log/cgn-nat444:session-log/cgn-nat444:secondary-log-type" {
    deviate add {
      must "/vsm:vsm/vsm:on-board-mode/vsm:mode='centralized-board'";
    }
  }
  deviation "/cgn-nat444:cgn-nat444/cgn-nat444:nat-instances/cgn-nat444:nat-instance/cgn-nat444:log/cgn-nat444:user-log" {
    deviate add {
      must "/vsm:vsm/vsm:on-board-mode/vsm:mode='centralized-board'";
    }
  }
  deviation "/cgn-nat444:cgn-nat444/cgn-nat444:nat-instances/cgn-nat444:nat-instance/cgn-nat444:log/cgn-nat444:hosts/cgn-nat444:host/cgn-nat444:secondary" {
    deviate delete {
      must "not (../secondary='true' and ../../../send-mode/mode='concurrent')";
    }
  }
  deviation "/cgn-nat444:cgn-nat444/cgn-nat444:nat-instances/cgn-nat444:nat-instance/cgn-nat444:statistics-enable/cgn-nat444:usage-statistics-enable/cgn-nat444:port-usage" {
    deviate add {
      must "/vsm:vsm/vsm:on-board-mode/vsm:mode='centralized-board'";
    }
  }
  deviation "/cgn-nat444:cgn-nat444/cgn-nat444:nat-instances/cgn-nat444:nat-instance/cgn-nat444:statistics-enable/cgn-nat444:usage-statistics-enable/cgn-nat444:session-usage" {
    deviate add {
      must "/vsm:vsm/vsm:on-board-mode/vsm:mode='centralized-board'";
    }
  }
  deviation "/cgn-nat444:cgn-nat444/cgn-nat444:nat-instances/cgn-nat444:nat-instance/cgn-nat444:statistics-enable/cgn-nat444:fast-forwarding" {
    deviate add {
      must "/vsm:vsm/vsm:on-board-mode/vsm:mode='centralized-board'";
    }
  }
  deviation "/cgn-nat444:cgn-nat444/cgn-nat444:nat-instances/cgn-nat444:nat-instance/cgn-nat444:inter-chassis-distributing" {
    deviate add {
      must "/vsm:vsm/vsm:on-board-mode/vsm:mode='centralized-board'";
    }
  }
  deviation "/cgn-nat444:cgn-nat444/cgn-nat444:nat-instances/cgn-nat444:nat-instance/cgn-nat444:port-reuse" {
    deviate add {
      must "/vsm:vsm/vsm:on-board-mode/vsm:mode='centralized-board'";
    }
  }
  deviation "/cgn-nat444:cgn-nat444/cgn-nat444:nat-instances/cgn-nat444:nat-instance/cgn-nat444:pcp/cgn-nat444:pcp-enable" {
    deviate add {
      must "/vsm:vsm/vsm:on-board-mode/vsm:mode='centralized-board'";
    }
  }
  deviation "/cgn-nat444:cgn-nat444/cgn-nat444:nat-instances/cgn-nat444:nat-instance/cgn-nat444:pcp/cgn-nat444:pcp-prefer-failure" {
    deviate add {
      must "/vsm:vsm/vsm:on-board-mode/vsm:mode='centralized-board'";
    }
  }
  deviation "/cgn-nat444:cgn-nat444/cgn-nat444:nat-instances/cgn-nat444:nat-instance/cgn-nat444:pcp/cgn-nat444:pcp-server/cgn-nat444:ipv4-server" {
    deviate add {
      must "/vsm:vsm/vsm:on-board-mode/vsm:mode='centralized-board'";
    }
  }
  deviation "/cgn-nat444:cgn-nat444/cgn-nat444:nat-instances/cgn-nat444:nat-instance/cgn-nat444:pcp/cgn-nat444:port-reservation" {
    deviate add {
      must "/vsm:vsm/vsm:on-board-mode/vsm:mode='centralized-board'";
    }
  }

}
