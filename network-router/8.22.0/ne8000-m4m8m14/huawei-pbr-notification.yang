/*
Copyright (C) 2019-2022 Huawei Technologies Co., Ltd. All rights reserved.
*/
module huawei-pbr-notification {
  yang-version 1;
  namespace "urn:huawei:yang:huawei-pbr-notification";
  prefix pbr-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of pbr.";
  revision 2022-07-20 {
    description
      "Modify rdr-type datatype.";
    reference
      "Huawei private.";
  }
  revision 2020-06-12 {
    description
      "Add new nodes.";
    reference
      "Huawei private.";
  }
  revision 2019-11-06 {
    description
      "Initial revision.";
    reference
      "Huawei private.";
  }
  ext:task-name "qos";
  
  typedef redirect-type {
    type enumeration {
      enum ipv4 {
        value 0;
        description
          "IPv4.";
      }
      enum ipv6 {
        value 1;
        description
          "IPv6.";
      }
    }
    description
      "Redirect type.";
  }
  notification xqos-redirect-nexthop-invalid-alarm {
    description
      "The redirect nexthop address did not match the network segment of the outbound interface.";
    leaf behavior-name {
      type string {
        length "1..127";
      }
      description
        "Behavior name.";
    }
    leaf redirect {
      type redirect-type;
      description
        "Redirect type.";
    }
    leaf interface-name {
      type string {
        length "1..511";
      }
      description
        "Interface name.";
    }
  }
  notification xqos-redirect-nexthop-invalid-alarm-resume {
    description
      "The redirect nexthop address matches the network segment of the outbound interface or the redirect configuration has been cleared.";
    leaf behavior-name {
      type string {
        length "1..127";
      }
      description
        "Behavior name.";
    }
    leaf redirect {
      type redirect-type;
      description
        "Redirect type.";
    }
    leaf interface-name {
      type string {
        length "1..511";
      }
      description
        "Interface name.";
    }
  }
  notification xqos-redirect-nexthop-lack-resource-alarm {
    description
      "Redirecting traffic to the next hop is invalid due to insufficient NHP resources.";
    leaf behavior-name {
      type string {
        length "1..127";
      }
      description
        "Behavior name.";
    }
    leaf slot-id {
      type string {
        length "1..16";
      }
      description
      "Slot ID.";
    }   
    leaf redirect-type {
      type redirect-type;
      description
        "Redirect type.";
    }
  }
  notification xqos-redirect-nexthop-lack-resource-alarm-resume {
    description
      "Resources are sufficient or the configuration of redirecting traffic to the next hop is deleted.";
    leaf behavior-name {
      type string {
        length "1..127";
      }
      description
        "Behavior name.";
    }
    leaf slot-id {
      type string {
        length "1..16";
      }
      description
      "Slot ID.";
    }   
    leaf redirect-type {
      type redirect-type;
      description
        "Redirect type.";
    }
  }
  notification xqos-interface-down-redirect-next-hop-invalid-alarm {
    description
      "Alarm when the interface goes down and the redirection next hop becomes invalid.";
    leaf rdr-type {
      type string {
        length "1..16";
      }
      description
        "Redirect type.";
    }
    leaf slot-id {
      type string {
        length "1..128";
      }
      description
        "Slot ID.";
    }
    leaf interface-name {
      type string {
        length "1..511";
      }
      description
        "Interface name.";
    }
    leaf behavior-name {
      type string {
        length "1..128";
      }
      description
        "Behavior name.";
    }
  }
  notification xqos-interface-down-redirect-next-hop-invalid-alarm-clear {
    description
      "Alarm clear when the interface goes up or the redirection next hop configuration is deleted.";
    leaf rdr-type {
      type string {
        length "1..16";
      }
      description
        "Redirect type.";
    }
    leaf slot-id {
      type string {
        length "1..128";
      }
      description
        "Slot ID.";
    }
    leaf interface-name {
      type string {
        length "1..511";
      }
      description
        "Interface name.";
    }
  }
  notification xqos-redirect-next-hop-event-log {
    description
      "Print log when route switching in scenarios where a redirection policy with no outbound interface specified is deployed.";
    leaf slot-id {
      type string {
        length "1..128";
      }
      description
        "Slot ID.";
    }
    leaf rdr-type {
      type string {
        length "1..16";
      }
      description
        "Redirect type.";
    }
    leaf ip-address {
      type string {
        length "1..128";
      }
      description
        "Ip address.";
    }
    leaf behavior-name {
      type string {
        length "1..128";
      }
      description
        "Behavior name.";
    }
  }
}
