/*
Copyright (C) 2019-2022 Huawei Technologies Co., Ltd. All rights reserved.
*/
module huawei-bras-cu-agent {
  namespace urn:huawei:yang:huawei-bras-cu-agent;
  prefix bras-cu-agent;
  import ietf-inet-types {
    prefix inet;
  }
  import huawei-ifm {
    prefix ifm;
  }
  import huawei-monitor-group {
    prefix monitor-group;
  }
  import huawei-route-monitor-group {
    prefix rmg;
  }
  import huawei-bfd {
    prefix bfd;
  }
  import huawei-fim-ifm {
    prefix fim-ifm;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "CU agent.";
  revision 2022-09-20 {
    description
      "Modify description.";
    reference
      "Huawei private.";
  }
  revision 2019-04-26 {
    description
      "Initial revision.";
    reference
      "Huawei private.";
  }
  ext:task-name "bras-control";
  typedef cu-mode-access-type {
    type enumeration {
      enum "layer2" {
        value 2;
        description
          "Layer2 access.";
      }
      enum "layer3" {
        value 3;
        description
          "Layer3 access.";
      }
      enum "layer3-leased-line" {
        value 4;
        description
          "Layer3 leased line.";
      }
    }
    description
      "CU mode access type.";
  }
  typedef cu-mode-type {
    type enumeration {
      enum "true" {
        value 1;
        description
          "CU mode is enabled.";
      }
    }
    description
      "CU mode type.";
  }
  container bras-cu-agent {
    description
      "Specify configuration information of CU agent.";
    container cu-agent {
      presence "Enable the UP mode so that the current device functions as a vBRAS-UP.";
      description
        "Enable/disable the UP mode so that the current device functions as a vBRAS-UP.";
      container interface-monitoring-groups {
        description
          "List of configuring a vBRAS-UP to track the session status of interface monitoring groups to detect network-side link faults.";
        list interface-monitoring-group {
          key "name";
          description
            "Configure a vBRAS-UP to track the session status of a specified interface monitoring group.";
          leaf name {
            type leafref {
              path "/monitor-group:monitor-group/monitor-group:groups/monitor-group:group/monitor-group:name";
            }
            description
              "Name of an interface monitoring group.";
          }
          leaf down-weight {
            type uint32 {
              range "1..32000";
            }
            mandatory true;
            description
              "Interface weight for reporting a network-side fault. A higher weight indicates a higher fault priority.";
          }
        }
      }
      container route-monitoring-groups {
        description
          "List of configuring a vBRAS-UP to track the session status of a route monitoring group to detect network-side link faults.";
        list route-monitoring-group {
          key "name";
          description
            "Configure a vBRAS-UP to track the session status of a specified route monitoring group.";
          leaf name {
            type leafref {
              path "/rmg:route-monitor-group/rmg:monitor-groups/rmg:monitor-group/rmg:group-name";
            }
            description
              "Name of a route monitoring group.";
          }
          leaf down-weight {
            type uint32 {
              range "1..32000";
            }
            mandatory true;
            description
              "Route weight for reporting a network-side fault. A higher weight indicates a higher fault priority.";
          }
        }
      }
      container bfd-sessions {
        description
          "List of configure a vBRAS-UP to track the status of a BFD session to detect access-side faults.";
        list bfd-session {
          key "name";
          description
            "Configure a vBRAS-UP to track the status of a BFD session.";
          leaf name {
            type leafref {
              path "/bfd:bfd/bfd:sessions/bfd:session/bfd:name";
            }
            description
              "Name of a BFD session.";
          }
        }
      }
      container link-bfd-sessions {
        description
          "List of configure link BFD sessions to monitor access-side faults on the vBRAS-UP.";
        list link-bfd-session {
          key "link-bfd-name";
          description
            "Configure link BFD session to monitor access-side faults on the vBRAS-UP.";
          leaf link-bfd-name {
            type leafref {
              path "/bfd:bfd/bfd:sessions/bfd:session/bfd:name";
            }
            must "/bfd:bfd/bfd:sessions/bfd:session[bfd:name=current()]/bfd:is-group-static-unicast-ipv4='true'";
            must "/bfd:bfd/bfd:sessions/bfd:session[bfd:name=current()]/bfd:destination-address-static-unicast-ipv4";
            must "/bfd:bfd/bfd:sessions/bfd:session[bfd:name=current()]/bfd:source-address-static-ipv4";
            description
              "Name of a BFD session.";
          }
          leaf interface-name {
            type leafref {
              path "/ifm:ifm/ifm:interfaces/ifm:interface/ifm:name";
            }
            must "/ifm:ifm/ifm:interfaces/ifm:interface[ifm:name=current()]/ifm:type='PW-VE'";
            must "/ifm:ifm/ifm:interfaces/ifm:interface[ifm:name=current()]/ifm:class='main-interface'";
            mandatory true;
            description
              "Specify an interface name.";
          }
        }
      }
      container up-nqa-detect {
        presence "Creat up-nqa-detect.";
        description
          "Enable/disable NQA dectct to the VXLAN tunnel.";
        leaf count {
          type uint32 {
            range "0..4294967295";
          }
          default "3";
          description
            "Number of sent Echo Request messages.";
        }
        leaf detect-time-type {
          type enumeration {
            enum "minute-level" {
              value 0;
              description
                "Minute level.";
            }
            enum "second-level" {
              value 1;
              description
                "Second level.";
            }
          }
          default "minute-level";
          description
            "Detect time type.";
        }
        leaf second-interval {
          when "../detect-time-type = 'second-level'";
          type uint32 {
            range "1..10000";
          }
          units s;
          default "60";
          description
            "Time elapses before a next Echo Request message is sent.";
          }
        leaf second-timeout {
          when "../detect-time-type = 'second-level'";
          type uint32 {
            range "1..65535";
          }
          units s;
          default "60";
          description
            "Timeout period of waiting for an Echo Reply message.";
        }
        leaf interval {
          when "../detect-time-type = 'minute-level'";
          type uint32 {
            range "1..10000";
          }
          units min;
          default "1";
          description
            "Time elapses before a next Echo Request message is sent.";
        }
        leaf timeout {
          when "../detect-time-type = 'minute-level'";
          type uint32 {
            range "1..65535";
          }
          units min;
          default "1";
          description
            "Timeout period of waiting for an Echo Reply message.";
        }
        leaf destination-port {
          type uint32 {
            range "1..65535";
          }
          mandatory true;
          description
            "Destination port number.";
        }
        leaf recovery-count {
          type uint32;
          default "1";
          description
            "Number of sent Echo Request messages, each ECHO_REQUEST packet has a response, the tunnel will Up.";
        }
      }
      container up-cusp-agent {
        config false;
        description
          "Operational state of binding a CUSP agent to the vBRAS-UP and the control tunnel between the vBRAS-CP and vBRAS-UP is established.";
        leaf name {
          type string {
            length "1..31";
          }
          description
            "Name of the CUSP agent bound to the control tunnel. After the CUSP agent is bound to the vBRAS-UP, the control tunnel between the vBRAS-CP and vBRAS-UP is established.";
        }
      }
      container up-vxlan-channels {
        config false;
        description
          "List of binding VxLAN Tunnel state.";
        list up-vxlan-channel {
          key "vni source-ip-address destination-ip-address";
          description
            "Binding VxLAN Tunnel state.";
          leaf vni {
            type uint32 {
              range "1..16777215";
            }
            description
              "VxLAN Network Identify.";
          }
          leaf source-ip-address {
            type inet:ipv4-address-no-zone;
            description
              "Source IP Address.";
          }
          leaf destination-ip-address {
            type inet:ipv4-address-no-zone;
            description
              "Destination IP Address.";
          }
          leaf vpn-instance-name {
            type string {
              length "1..31";
            }
            description
              "VPN Instance Name.";
          }
        }
      }
      container cusp-bfd-groups {
        description
          "List of configure a vBRAS-UP to track the status of a BFD session group to detect control tunnel status.";
        list cusp-bfd-group {
          key "name";
          max-elements "2";
          description
            "Configure a vBRAS-UP to track the status of a BFD session group.";
          leaf name {
            type leafref {
              path "/bfd:bfd/bfd:sessions/bfd:session/bfd:name";
            }
            must "/bfd:bfd/bfd:sessions/bfd:session[bfd:name=current()]/bfd:is-group-static-unicast-ipv4='true'";
            description
              "Name of a BFD session group.";
          }
        }
      }
    }
    container up-versions {
      config false;
      description
        "List of Checking CU interface version information on the UP side state.";
      list up-version {
        key instance;
        description
          "Checking CU interface version information on the UP side state.";
        leaf instance {
          type enumeration {
            enum master {
              value 0;
              description
                "Master type.";
            }
            enum slave {
              value 1;
              description
                "Slave type.";
            }
            enum no-disaster-environment {
              value 255;
              description
                "Not disaster environment.";
            }
          }
          description
            "UP connect with multiple CP.";
        }
        leaf cp-version {
          type string {
            length 1..7;
          }
          description
            "CP version information.";
        }
        leaf up-version {
          type string {
            length 1..7;
          }
          description
            "UP version information.";
        }
        leaf negotiation-result {
          type string {
            length 1..15;
          }
          description
            "Negotiation result.";
        }
      }
    }
    container disaster-recoverys {
      config false;
      description
        "List of disaster recovery configurations on a vBRAS-UP.";
      list disaster-recovery {
        key "cp-address";
        description
          "Display disaster recovery configurations on a vBRAS-UP statistics.";
        leaf cp-address {
          type inet:ipv4-address-no-zone;
          description
            "Source IP address used to establish a connection between the vBRAS-CP and vBRAS-UP.";
        }
        leaf master-address {
          type inet:ipv4-address-no-zone;
          description
            "IP address of the master vBRAS-CP.";
        }
        leaf slave-address {
          type inet:ipv4-address-no-zone;
          description
            "IP address of the backup vBRAS-CP.";
        }
        leaf openflow-address {
          type inet:ipv4-address-no-zone;
          description
            "IP address of an control channel.";
        }
        leaf vxlan-address {
          type inet:ipv4-address-no-zone;
          description
            "IP address of a protocol channel.";
        }
        leaf priority {
          type uint32;
          description
            "Priority of the vBRAS-CP master/backup role.";
        }
        leaf negotiation-master-address {
          type inet:ipv4-address-no-zone;
          description
            "Negotiation result IP address of the master vBRAS-CP.";
        }
        leaf negotiation-slave-address {
          type inet:ipv4-address-no-zone;
          description
            "Negotiation result IP address of the backup vBRAS-CP.";
        }
      }
    }
  }
  augment "/ifm:ifm/ifm:interfaces/ifm:interface" {
    description
      "Configure CU agent to interface model.";
    container cu-agent {
      description
        "Configure CU agent to interface model.";
      container up-ve-track {
        when "../../ifm:type = 'Virtual-Ethernet' and ../../ifm:class='main-interface'";
        description
          "Configure the UP VE port to track the status of the UP/CP channel (including CUSP and VXLAN).";
        leaf up-ve-track-tunnel-enable {
          type empty;
          description
            "Enable the UP VE port to track the status of the UP/CP channel (including CUSP and VXLAN).";
        }
      }
      container cu-multicast-rbp {
        when "(../../ifm:type='Virtual-Ethernet' or
              ../../ifm:type='100GE' or
              ../../ifm:type='400GE' or
              ../../ifm:type='25GE' or
              ../../ifm:type='50GE' or
              ../../ifm:type='50|100GE' or
              ../../ifm:type='GigabitEthernet' or
              ../../ifm:type='Eth-Trunk') and ../../ifm:class='main-interface'";
        description
          "Configure an RBP to a specified interface on a vBRAS-UP.";
        leaf name {
          type string {
            length "1..128";
          }
          must "/bras-cu-agent:bras-cu-agent/bras-cu-agent:cu-agent";
          must "(../../../ifm:type='Virtual-Ethernet' and ../../../fim-ifm:ve-group/fim-ifm:type='L3VE') or ../../../ifm:type!='Virtual-Ethernet'";
          description
            "Bind an RBP to a specified interface on a vBRAS-UP.";
        }
      }
      container cu-mode-interface {
        config false;
        description
          "Operational state of the UP mode in the interface and report the interface to the vBRAS-CP for management.";
        leaf cu-mode-enable {
          type cu-mode-type;
          description
            "Enable/disable CU mode.";
        }
        leaf user-access-type {
          type cu-mode-access-type;
          description
            "Access type of a user.";
        }
      }
    }    
  }
}
