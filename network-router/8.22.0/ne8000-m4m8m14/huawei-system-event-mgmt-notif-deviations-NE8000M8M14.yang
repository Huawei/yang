/*
Copyright (C) 2021 Huawei Technologies Co., Ltd. All rights reserved.
*/
module huawei-system-event-mgmt-notif-deviations-NE8000M8M14 {
  namespace "urn:huawei:yang:huawei-system-event-mgmt-notif-deviations-NE8000M8M14";
  prefix system-event-mgmt-notif-devs-NE8000M8M14;

  import huawei-system-event-mgmt-notif {
    prefix system-event-mgmt-notif;
  }

  organization
    "Huawei Technologies Co., Ltd.";
  contact
    "Huawei Industrial Base
     Bantian, Longgang
     Shenzhen 518129
     People's Republic of China
     Website: http://www.huawei.com
     Email: support@huawei.com";
  description
    "This module defines deviation statements for huawei-system-event-mgmt-notif module.";

  revision 2021-05-07 {
    description
      "Initial revision.";
    reference "Huawei private.";
  }

  deviation "/system-event-mgmt-notif:board-leave-master" {
    deviate not-supported;
  }
  deviation "/system-event-mgmt-notif:board-become-master" {
    deviate not-supported;
  }
}
