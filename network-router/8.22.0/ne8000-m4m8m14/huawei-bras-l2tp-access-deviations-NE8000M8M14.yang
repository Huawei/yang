/*
Copyright (C) 2021 Huawei Technologies Co., Ltd. All rights reserved.
*/
module huawei-bras-l2tp-access-deviations-NE8000M8M14 {
  namespace "urn:huawei:yang:huawei-bras-l2tp-access-deviations-NE8000M8M14";
  prefix bras-l2tp-access-devs-NE8000M8M14;

  import huawei-bras-l2tp-access {
    prefix bras-l2tp-access;
  }

  import huawei-extension {
    prefix ext;
  }

  import huawei-bras-cu-controller {
    prefix bras-cu-controller;
  }

  import huawei-devm-vnf {
    prefix devm-vnf;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-l2tp-access module.";

  revision 2021-05-07 {
    description
      "Initial revision.";
    reference
      "Huawei private.";
  }

  deviation "/bras-l2tp-access:bras-l2tp-access/bras-l2tp-access:l2tp-groups/bras-l2tp-access:l2tp-group/bras-l2tp-access:l2tp-lac/bras-l2tp-access:cp-source-interfaces" {
    deviate not-supported;
  }
  deviation "/bras-l2tp-access:bras-l2tp-access/bras-l2tp-access:l2tp-groups/bras-l2tp-access:l2tp-group/bras-l2tp-access:cp-source-interface" {
    deviate not-supported;
  }
  deviation "/bras-l2tp-access:bras-l2tp-access/bras-l2tp-access:lns-groups/bras-l2tp-access:lns-group/bras-l2tp-access:bind-board/bras-l2tp-access:bind-backup-groups" {
    deviate not-supported;
  }
  deviation "/bras-l2tp-access:bras-l2tp-access/bras-l2tp-access:lns-backup-groups" {
    deviate not-supported;
  }
  deviation "/bras-l2tp-access:bras-l2tp-access/bras-l2tp-access:l2tp-failover" {
    deviate not-supported;
  }
  deviation "/bras-l2tp-access:bras-l2tp-access/bras-l2tp-access:cu-lac-tunnels" {
    deviate not-supported;
  }
  deviation "/bras-l2tp-access:bras-l2tp-access/bras-l2tp-access:cu-lac-sessions" {
    deviate not-supported;
  }
  deviation "/bras-l2tp-access:bras-l2tp-access/bras-l2tp-access:lns-tunnel-backups" {
    deviate not-supported;
  }
  deviation "/bras-l2tp-access:bras-l2tp-access/bras-l2tp-access:lns-session-backups" {
    deviate not-supported;
  }
  deviation "/bras-l2tp-access:bras-l2tp-access/bras-l2tp-access:cp-lns-statistics" {
    deviate not-supported;
  }
  deviation "/bras-l2tp-access:bras-l2tp-access/bras-l2tp-access:disaster-statistics" {
    deviate not-supported;
  }
  deviation "/bras-l2tp-access:reset-cu-lac-tunnels" {
    deviate not-supported;
  }
  deviation "/bras-l2tp-access:reset-cp-lns-statistics" {
    deviate not-supported;
  }
  deviation "/bras-l2tp-access:cu-reset-down-lns" {
    deviate not-supported;
  }
  deviation "/devm:devm/devm:lpu-boards/devm:lpu-board/bras-l2tp-access:l2tp" {
    deviate not-supported;
  }
  deviation "/bras-cu-controller:bras-cu-controller/bras-cu-controller:resource-ups/bras-cu-controller:resource-up/bras-l2tp-access:l2tp" {
    deviate not-supported;
  }
  deviation "/bras-cu-controller:bras-cu-controller/bras-cu-controller:resource-ups/bras-cu-controller:resource-up/bras-cu-controller:remote-up-boards/bras-cu-controller:remote-up-board/bras-l2tp-access:l2tp" {
    deviate not-supported;
  }
  deviation "/devm-vnf:devm-vnf/devm-vnf:vnf-boards/devm-vnf:vnf-board/bras-l2tp-access:l2tp" {
    deviate not-supported;
  }
  deviation "/bras-l2tp-access:bras-l2tp-access/bras-l2tp-access:lns-global/bras-l2tp-access:tunnel-limit/bras-l2tp-access:limit/bras-l2tp-access:set-value" {
    deviate replace {
      type uint32 {
        range "0..16384";
      }
    }
    deviate replace {
      default "16384";
    }
  }
  deviation "/bras-l2tp-access:bras-l2tp-access/bras-l2tp-access:lns-global/bras-l2tp-access:lns-fast-replys/bras-l2tp-access:lns-fast-reply/bras-l2tp-access:slot-id" {
    deviate replace {
      type leafref {
        path "/devm:devm/devm:mpu-boards/devm:mpu-board/devm:position";
      }
    }
  }
  deviation "/bras-l2tp-access:bras-l2tp-access/bras-l2tp-access:lns-global/bras-l2tp-access:slot-block/bras-l2tp-access:slot-id" {
    deviate replace {
      type leafref {
        path "/devm:devm/devm:mpu-boards/devm:mpu-board/devm:position";
      }
    }
  }
  deviation "/bras-l2tp-access:bras-l2tp-access/bras-l2tp-access:lns-global/bras-l2tp-access:l2tp-aaa/bras-l2tp-access:lns-user-limit/bras-l2tp-access:limit-value" {
    deviate replace {
      type uint32 {
        range "0..65536";
      }
    }
  }
  deviation "/bras-l2tp-access:bras-l2tp-access/bras-l2tp-access:l2tp-groups/bras-l2tp-access:l2tp-group/bras-l2tp-access:l2tp-lac/bras-l2tp-access:other-function-sets/bras-l2tp-access:session-limit" {
    deviate replace {
      type uint32 {
        range "0..65535";
      }
    }
    deviate delete {
      default "65535";
    }
  }
  ext:deviation-ext "/bras-l2tp-access:bras-l2tp-access/bras-l2tp-access:l2tp-groups/bras-l2tp-access:l2tp-group/bras-l2tp-access:l2tp-lac/bras-l2tp-access:other-function-sets/bras-l2tp-access:session-limit" {
    ext:deviate-ext add {
      ext:dynamic-default {
        ext:default-value "65535" {
          description "The default value or the maximum value for IPU-2T and IPU-1T2 boards is 65535.";
        }
        ext:default-value "32767" {
          description "The default value or the maximum value for IPU-1T2-A/IPU-1T2-B and IPUA-1T2-A/IPU-1T2-B boards is 32767.";
        }
      }
    }
  }
  deviation "/bras-l2tp-access:bras-l2tp-access/bras-l2tp-access:lns-groups/bras-l2tp-access:lns-group/bras-l2tp-access:bind-board/bras-l2tp-access:bind-slots/bras-l2tp-access:bind-slots/bras-l2tp-access:bind-slot/bras-l2tp-access:slot-id" {
    deviate replace {
      type leafref {
        path "/devm:devm/devm:mpu-boards/devm:mpu-board/devm:position";
      }
    }
  }
  deviation "/bras-l2tp-access:reset-lns-tunnels/bras-l2tp-access:input/bras-l2tp-access:slot" {
    deviate replace {
      type leafref {
        path "/devm:devm/devm:mpu-boards/devm:mpu-board/devm:position";
      }
    }
  }
  deviation "/bras-l2tp-access:reset-l2tp-user-urpf-discard/bras-l2tp-access:input/bras-l2tp-access:slot" {
    deviate replace {
      type leafref {
        path "/devm:devm/devm:mpu-boards/devm:mpu-board/devm:position";
      }
    }
  }

}
