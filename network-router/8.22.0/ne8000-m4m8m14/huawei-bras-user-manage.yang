/*
Copyright (C) 2019-2022 Huawei Technologies Co., Ltd. All rights reserved.
*/
module huawei-bras-user-manage {
  namespace urn:huawei:yang:huawei-bras-user-manage;
  prefix bras-user-manage;
  
  import huawei-ifm {
    prefix ifm;
  }
  import huawei-aaa {
    prefix aaa;
  }
  import huawei-bras-basic-access {
    prefix bras-basic-access;
  }
  import huawei-pub-type {
    prefix pub-type;
  }
  import ietf-inet-types {
    prefix inet;
  }
  import huawei-extension {
    prefix ext;
  }
  import huawei-devm {
    prefix devm;
  }
  import huawei-devm-vnf {
    prefix devm-vnf;
  }
  import huawei-qos {
    prefix qos;
  }
  import huawei-network-instance {
    prefix ni;
  }
  import huawei-l3vpn {
    prefix l3vpn;
  }
  import huawei-radius {
    prefix radius;
  }
  import huawei-time-range {
    prefix timerange;
  }
  import huawei-ifm-trunk {
    prefix ifm-trunk;
  }
  import huawei-ethernet {
    prefix ethernet;
  }
  import huawei-ssl {
    prefix ssl;
  }
  import huawei-bras-cu-controller {
    prefix bras-cu-controller;
  }
  import huawei-bras-ipv4-address-manage {
    prefix bras-ipv4-address-manage;
  }
  import huawei-bras-ipv6-address-manage {
    prefix bras-ipv6-address-manage;
  }
  include huawei-bras-user-manage-type;

  organization
    "Huawei Technologies Co., Ltd.";
  contact
    "Huawei Industrial Base
     Bantian, Longgang
     Shenzhen 518129
     People's Republic of China
     Website: http://www.huawei.com
     Email: support@huawei.com";
  description
    "Bras user manage.";
  revision 2022-10-10 {
    description
      "Modify description.";
    reference
      "Huawei private.";
  }
  revision 2019-04-04 {
    description
      "Initial revision.";
    reference
      "Huawei private.";
  }
  ext:task-name "bras-control";

  grouping option60-vendorclass-cfg {
    description
      "Configures the vendor-class (DHCPv4 option60/DHCPv6 option16).";
    leaf encrypt {
      type boolean;
      default "false";
      description
        "Enable/disable the VENDOR-CLASS (DHCPv4 OPTION60/DHCPv6 OPTION16) field value.";
    }
    leaf partial-match {
      type enumeration {
        enum "domain-included" {
          value 0;
          description
            "Specifies the customized options of the vendor contains domain name.";
        }
        enum "included-in-domain" {
          value 1;
          description
            "Specifies the customized options of the vendor contains a part of domain name.";
        }
      }
      description
        "Sets domainInclude or includeInDomain business.";
    }
    choice partial-info {
      description
        "Configures part of the vendor-class (DHCPv4 option60/DHCPv6 option16) attribute to identify domain names.";
      case cn {
        description
          "Indicates that the system uses the CN format to identify domain names.";
        leaf cn {
          type empty;
          description
            "Indicates that the system uses the CN format to identify domain names.";
        }
      }
      case not-cn {
        description
          "Indicates that the system does not use the CN format to identify domain names.";
        leaf offset-value {
          when "../length or ../sub-option-value"; 
          type uint16 {
            range "1..254";
          }
          description
            "Indicates that the system does not use the CN format to identify domain names.";
        }
        choice length-or-sub-option {
          description
            "Configures the field length or sub-option code of the vendor-class attribute to identify domain names.";
          case length {
            description
              "Configures the field length of the vendor-class attribute to identify domain names.";
            leaf length {
              type uint16 {
                range "1..254";
              }
              description
                "Configures the field length of the vendor-class attribute to identify domain names.";
            }
          }
          case sub-option {
            description
              "Configures the sub-option code of the vendor-class attribute to identify domain names.";
            leaf sub-option-value {
              type uint16 {
                range "1..255";
              }
              description
                "Configures the sub-option code of the vendor-class attribute to identify domain names..";
            }
            leaf sub-offset-value {
              when "../sub-option-value"; 
              type uint16 {
                range "1..254";
              }
              description
                "Configures the offset value of a vendor-class sub-option to identify domain names.";
            }
            leaf sub-length-value {
              when "../sub-option-value"; 
              type uint16 {
                range "1..254";
              }
              description
                "Configures the field length of a vendor-class sub-option to identify domain names.";
            }
          }
        }
      }
    }
  }
  grouping access-table-qos-info {
    description
      "Qos information.";
    leaf qos-profile-name {
      type string {
        length "1..63";
      }
      config false;
      description
        "Inbound QOS profile name.";
    }
    leaf qos-config-type {
      type bras-user-manage-qos-config-type;
      config false;
      description
        "Inbound QOS configuration type.";
    }
    leaf qos-effective-type {
      type bras-user-manage-qos-effective-type;
      config false;
      description
        "Inbound QOS effective type.";
    }
    leaf sq-cir {
      type uint64 {
        range "0..4294967295";
      }
      units kbit/s;
      config false;
      description
        "Inbound user queue CIR.";
    }
    leaf sq-cir-config-type {
      type bras-user-manage-qos-config-type;
      config false;
      description
        "Inbound user queue CIR configuration type.";
    }
    leaf sq-pir {
      type uint64 {
        range "0..4294967295";
      }
      units kbit/s;
      config false;
      description
        "Inbound user queue PIR.";
    }
    leaf sq-pir-config-type {
      type bras-user-manage-qos-config-type;
      config false;
      description
        "Inbound user queue PIR configuration type.";
    }
    leaf car-cir {
      type uint64 {
        range "0..4294967295";
      }
      units kbit/s;
      config false;
      description
        "Inbound car Cir.";
    }
    leaf car-cir-config-type {
      type bras-user-manage-qos-config-type;
      config false;
      description
        "Inbound car Cir configuration type.";
    }
    leaf car-pir {
      type uint64 {
        range "0..4294967295";
      }
      units kbit/s;
      config false;
      description
        "Inbound car Pir.";
    }
    leaf car-pir-config-type {
      type bras-user-manage-qos-config-type;
      config false;
      description
        "Inbound car Pir configuration type.";
    }
    leaf car-cbs {
      type uint64 {
        range "0..4294967295";
      }
      units Byte;
      config false;
      description
        "Inbound car Cbs.";
    }
    leaf car-cbs-config-type {
      type bras-user-manage-qos-config-type;
      config false;
      description
        "Inbound car Cbs configuration type.";
    }
    leaf car-pbs {
      type uint64 {
        range "0..4294967295";
      }
      units Byte;
      config false;
      description
        "Inbound car Pbs.";
    }
    leaf car-pbs-config-type {
      type bras-user-manage-qos-config-type;
      config false;
      description
        "Inbound car Pbs configuration type.";
    }
  }
  grouping bas-view-group {
    description
      "Bras user manage nodes group in bas interface.";
    container service-identify-policy {
      description
        "Configure the service identification policy is applied in bas interface.";
      leaf name {
        type leafref {
          path "/bras-user-manage:bras-user-manage/bras-user-manage:service-identify-policys/bras-user-manage:service-identify-policy/bras-user-manage:name";
        }
        description
          "Service identification policy name.";
      }
    }
  }
  grouping access-user-resource-usage {
    description
      "The user resource usage of the main control board and interface boards.";
    leaf user-usage {
      type uint8 {
        range "0..100";
      }
      units %;
      description
        "User usage.";
    }
    leaf total-user-number {
      type uint32;
      description
        "Total number of users allowed.";
    }
    leaf used-user-number {
      type uint32;
      description
        "Number of used users.";
    }
  }
  grouping max-online-user-by-slot {
    description
      "The max online users on the history.";
    leaf max-online-users {
      type uint32;
      description
        "Max online users since startup.";
    }
    leaf max-online-time {
      type string {
        length "1..31";
      }
      description
        "Time of max online users.";
    }
    leaf max-accounting-ready-users {
      type uint32;
      description
        "Max accounting-ready users since startup.";
    }
    leaf max-accounting-ready-time {
      type string {
        length "1..31";
      }
      description
        "Time of max accounting-ready users.";
    }
  }
  grouping max-online-user {
    description
      "The max online users on the history.";
    uses max-online-user-by-slot;
    leaf max-normal-rui-local-users {
      type uint32;
      description
        "Max normal and RUI local users since startup.";
    }
    leaf max-normal-rui-local-time {
      type string {
        length "1..31";
      }
      description
        "Time of max normal and RUI local users.";
    }
    leaf max-rui-remote-users {
      type uint32;
      description
        "Max RUI remote users since startup.";
    }
    leaf max-rui-remote-time {
      type string {
        length "1..31";
      }
      description
        "Time of max RUI remote users.";
    }
  }
  grouping domain-max-online-user-info-type {
    description
      "The max online users on the history.";
    leaf max-online-users {
      type uint32;
      description
        "Max online users since startup.";
    }
    leaf max-online-time {
      type string {
        length "1..31";
      }
      description
        "Time of max online users.";
    }
    leaf max-online-reset-time {
      type string {
        length "1..31";
      }
      description
        "Reset time of max online users.";
    }
  }
  grouping block-interface {
    description
      "The command blocks a BAS interface.";
    container block {
      description
        "Configure the status to be block.";
        leaf enable {
          type boolean;
          default "false";
          description
            "Enable/disable the status to be block.";
        }
    }
  }
  grouping default-password {
    description
      "The default-password sets the password of an IPoX user. By default, the password of an IPoX user is VLAN.";
    leaf password-format {
      type enumeration {
        enum "password" {
          value 1;
          description
            "Indicates that the user password is in ciphertext. Specifies a ciphertext password. The password is case sensitive and does not contain command line characters such as blanks and question mark.";
        }
        enum "user-class" {
          value 2;
          description
            "User's user-class (dhcpv4 option77/dhcpv6 option15).";
        }
        enum "vendor-class" {
          value 3;
          description
            "User's vendor-class (dhcpv4 option60/dhcpv6 option16).";
        }
        enum "option60" {
          value 4;
          description
            "User's vendor-class (dhcpv4 option60/dhcpv6 option16).";
        }
        enum "option77" {
          value 5;
          description
            "User's user-class (dhcpv4 option77/dhcpv6 option15).";
        }
      }
      mandatory true;
      description
        "Indicates the format of user password.";
    }
    leaf password-value {
      when "../password-format='password'";
      type pub-type:password-extend {
        length "1..268";
      }
      mandatory true;
      description
        "Indicates that the user password is in ciphertext. Specifies a ciphertext password. The password is case sensitive and does not contain command line characters such as blanks and question mark.";
    }
    leaf vendor-class-format {
      when "../password-format='vendor-class' or ../password-format='option60'";
      type enumeration {
        enum "cn" {
          value 1;
          description
            "Indicates that the system uses the vendor-class attribute of the Cn-telecom format as the user password.";
        }
        enum "length-defined" {
          value 2;
          description
            "Configures the field length of the vendor-class attribute as the user password.";
        }
        enum "sub-option" {
          value 3;
          description
            "Configures the sub-option code of the vendor-class attribute as the user password.";
        }
      }
      description
        "Configures the format of the vendor-class attribute as the user password.";
    }
    leaf vendor-class-offset-value {
      when "../vendor-class-format='length-defined' or ../vendor-class-format='sub-option'";
      type uint32 {
        range "0..255";
      }
      description
        "Configures the offset of a vendor-class option as the user password.";
    }
    leaf vendor-class-length-value {
      when "../vendor-class-format='length-defined'";
      type uint32 {
        range "0..255";
      }
      mandatory true;
      description
        "Configures the field length of the vendor-class attribute as the user password.";
    }
    leaf vendor-class-sub-option-code {
      when "../vendor-class-format='sub-option'";
      type uint32 {
        range "0..255";
      }
      mandatory true;
      description
        "Configures the sub-option code of the vendor-class attribute as the user password.";
    }
    leaf vendor-class-sub-offset {
      when "../vendor-class-format='sub-option'";
      type uint32 {
        range "0..255";
      }
      description
        "Configures the offset of a vendor-class sub-option code as the user password.";
    }
    leaf vendor-class-sub-length {
      when "../vendor-class-format='sub-option'";
      type uint32 {
        range "0..255";
      }
      description
        "Configures the field length of a vendor-class sub-option as the user password.";
    }
    leaf md5-encrypt {
      when "../password-format='vendor-class' or ../password-format='option60'";
      type boolean;
      default "false";
      description
        "Enable/disable the system uses the MD5 algorithm to encrypt the user password.";
    }
    leaf support-hex {
      when "../password-format='vendor-class' or ../password-format='option60'";
      type boolean;
      default "false";
      description
        "Enable/disable the user password supports Hex.";
    }
  }
  grouping default-password-template {
    description
      "The default-password-template command binds a user password template to a BAS interface.";
    container default-password-template {
      description
        "Configure a user password template in a BAS interface.";
      leaf name {
        type leafref {
          path "/bras-user-manage:bras-user-manage/bras-user-manage:default-password-templates/bras-user-manage:default-password-template/bras-user-manage:template-name";
        }
        description
          "Specifies a user password template name.";
      }
    }
  }
  grouping flow-statistics-information {
    description
      "User traffic statistics based on a specified inner or outer VLAN ID on a device.";
    leaf input-packet {
      type uint64;
      units packet;
      description
        "Number of upstream packets.";
    }
    leaf input-byte {
      type uint64;
      units Byte;
      description
        "Number of upstream bytes.";
    }
    leaf output-packet {
      type uint64;
      units packet;
      description
        "Number of downstream packets.";
    }
    leaf output-byte {
      type uint64;
      units Byte;
      description
        "Number of downstream bytes.";
    }
    leaf ipv4-input-packet {
      type uint64;
      units packet;
      description
        "Number of upstream IPv4 packets.";
    }
    leaf ipv4-input-byte {
      type uint64;
      units Byte;
      description
        "Number of upstream IPv4 bytes.";
    }
    leaf ipv4-output-packet {
      type uint64;
      units packet;
      description
        "Number of downstream IPv4 packets.";
    }
    leaf ipv4-output-byte {
      type uint64;
      units Byte;
      description
        "Number of downstream IPv4 bytes.";
    }
    leaf ipv6-input-packet {
      type uint64;
      units packet;
      description
        "Number of upstream IPv6 packets.";
    }
    leaf ipv6-input-byte {
      type uint64;
      units Byte;
      description
        "Number of upstream IPv6 bytes.";
    }
    leaf ipv6-output-packet {
      type uint64;
      units packet;
      description
        "Number of downstream IPv6 packets.";
    }
    leaf ipv6-output-byte {
      type uint64;
      units Byte;
      description
        "Number of downstream IPv6 bytes.";
    }
  }
  grouping online-user-number {
    description
      "Number of online users.";
    leaf total-users {
      type uint32;
      description
        "Total users.";
    }
    leaf ipv4-users {
      type uint32;
      description
        "IPv4 users.";
    }
    leaf ipv6-users {
      type uint32;
      description
        "IPv6 users.";
    }
    leaf dual-users {
      type uint32;
      description
        "Dual-stack online users.";
    }
  }
  grouping access-sub-option-group {
    description 
      "Access line id sub option grouping.";
    leaf offset {
      type uint8 {
        range "0..127";
      }
      default "0";
      description
        "Specifies the offset value of the sub-option.";
    }
    leaf parse-mode {
      type enumeration {
        enum "string" {
          value 1;
          description
            "Indicates that the system parses Option82 in string. length-value specifies the length of the sub-option of dhcpv4 option82 or dhcpv6 option18+37.";
        }
        enum "binary" {
          value 2;
          description
            "Indicates that the system parses the sub-option of dhcpv4 option82 or dhcpv6 option18+37 in binary. length-value specifies the length of the sub-option of dhcpv4 option82 or dhcpv6 option18+37.";
        }
        enum "hex" {
          value 3;
          description
            "Indicates that the system parses Option82 in hex. length-value specifies the length of the sub-option of dhcpv4 option82 or dhcpv6 option18+37.";
        }
        enum "auto-identify" {
          value 4;
          description
            "Auto identify.";
        }
      }
      mandatory true;
      description
        "Indicates the parse mode of the sub-option of dhcpv4 option82.";
    }
    leaf length {
      when "../parse-mode!='binary'";
      type uint8 {
        range "1..64";
      }
      description
        "Configures the field length of a vendor-class sub-option for the user name.";
    }
    leaf binary-length {
      when "../parse-mode='binary'";
      type uint8 {
        range "1|2|4";
      }
      mandatory true;
      description
        "Configures the binary length of a vendor-class sub-option for the user name.";
    }
    leaf hex-class {
      when "../parse-mode='hex'";
      type enumeration {
        enum "class1" {
          value 1;
          description
            "Indicates that the option information is printed in the format of HHHHHHHHHHHH during the parsing of hexadecimal codes.";
        }
        enum "class2" {
          value 2;
          description
            "Indicates that the option information is printed in the format of HH-HH-HH-HH-HH-HH during the parsing of hexadecimal codes.";
        }
        enum "class3" {
          value 3;
          description
            "Indicates that the option information is printed in the format of HHHH-HHHH-HHHH during the parsing of hexadecimal codes.";
        }
      }
      mandatory true;
      description
        "Sub-option format class.";
    }
    leaf sub-option-seperator {
      type string {
        length "1";
        pattern "[^\"?cCdDgGiImMoOpPsSvV]";
      }
      must "not(/bras-user-manage:bras-user-manage/bras-user-manage:default-user-name-templates/bras-user-manage:default-user-name-template/bras-user-manage:include-types/bras-user-manage:include-type/bras-user-manage:seperator)";
      description
        "Configures the sub option seperator.";
    }
  }
  
  grouping include-type-group {
    description
      "The include type attributes group.";
    leaf type {
      type bras-user-manage-include-type;
      description
        "Configures the parameter of default user name.";
    }
    leaf seperator {
      type string {
        length "1";
        pattern "[^\"?aAcCdDgGiImMoOpPsSuUvV]";
      }
      description
        "Configures the user-defined format of the attribute seperator.";
    }
    container gateway-address {
      when "../type='gateway-address'";
      description
        "Configure the seperator of the gateway address.";
      leaf gateway-seperator {
        type string {
          length "1";
          pattern "[^\"?]";
        }
        mandatory true;
        description
          "Seperator of the gateway address.";
      }
    }
    container ip-address {
      when "../type='ip-address'";
      description
        "Configure the seperator of the IP address.";
      leaf ip-seperator {
        type string {
          length "1";
          pattern "[^\"?]";
        }
        mandatory true;
        description
          "Seperator of the IP address.";
      }
    }
    container ipv6-preferred-address {
      when "../type='ipv6-preferred-address'";
      description
        "Configure the seperator of the preferred format IPv6 address.";
      leaf ipv6-seperator {
        type string {
          length "1";
          pattern "[^\"?]";
        }
        mandatory true;
        description
          "Seperator of the preferred format IPv6 address.";
      }
    }
    container mac-address {
      when "../type='mac-address'";
      description
        "Configure the seperator of the MAC address.";
      leaf mac-seperator {
        type string {
          length "1";
          pattern "[^\"?nN]";
        }
        description
          "Seperator of the MAC address.";
      }
    }
    container option82-sub-options {
      when "../type='option82'";
      description
        "List of option82 sub option.";
      list option82-sub-option {
        key "position";
        max-elements "4";
        description
          "Configure option82 sub option.";
        leaf position {
          type uint8 {
            range "1..4";
          }
          description
            "Specifies sub option position.";
        }
        leaf id {
          type uint8 {
            range "1..2";
          }
          mandatory true;
          description
            "Specifies sub option id.";
        }
        uses access-sub-option-group;
      }
    }
    container access-line-id-sub-options {
      when "../type='access-line-id'";
      description
        "List of access line id sub options.";
      list access-line-id-sub-option {
        key "type";
        unique "position";
        description
          "Configure access line id sub option.";
        leaf type {
          type enumeration {
            enum "circuit-id" {
              value 2;
              description
                "Indicates that the system uses dhcpv6 option18 contained in the access request packet as the user name.";
            }
            enum "remote-id" {
              value 3;
              description
                "Indicates that the system uses dhcpv6 option37 contained in the access request packet as the user name.";
            }
          }
          description
            "Specifies access line id type.";
        }
        leaf position {
          type uint8 {
            range "1..2";
          }
          mandatory true;
          description
            "Specifies access line id position.";
        }
        uses access-sub-option-group;
      }
    }
    container option60-format {
      when "../type='option60' or ../type='vendor-class'";
      description
        "Configure the option60 or vendor-class format.";
      choice option-format {
        description
          "Configures the option60 or vendor-class format.";
        case cn-telecom {
          description
            "CN telecom format.";
          leaf enable {
            type empty;
            description
              "Enable cn telecom format.";
          }
        }
        case standard {
          description
            "Standard format.";
          leaf option-offset {
            type uint16 {
              range "1..254";
            }
            description
              "Configures the offset of a vendor-class option for user name.";
          }
          choice option {
            mandatory true;
            description
              "Configure option parameter.";
            case length {
              description
                "Configures the length of a vendor-class sub-option for user name.";
              leaf option-length {
                type uint16 {
                  range "1..254";
                }
                description
                  "Configures the field length of the vendor-class attribute for the user name.";
              }
            }
            case sub-option {
              description
                "Configures the suboption code of the vendor-class attribute for user name.";
              leaf sub-id {
                type uint16 {
                  range "1..255";
                }
                mandatory true;
                description
                  "Configures the suboption code of the vendor-class attribute for user name.";
              }
              leaf sub-offset {
                type uint16 {
                  range "1..254";
                }
                description
                  "Configures the offset of a vendor-class sub-option code for the user name.";
              }
              leaf sub-length {
                type uint16 {
                  range "1..254";
                }
                description
                  "Configures the field length of a vendor-class sub-option for the user name.";
              }
            }
          }
        }
      }
    }
  }
  grouping template-default-user-name-group {
    description
      "List of the creation mode for the pure user names of IPoX or pppoe users.";
    container include-types {
      must "not((count(include-type[type='client-id'])>0) and (count(include-type[type='option61'])>0))";
      must "not((count(include-type[type='option60'])>0) and (count(include-type[type='vendor-class'])>0))";
      must "not((count(include-type[type='option82'])>0) and (count(include-type[type='access-line-id'])>0))";
      description
        "List of the creation mode for the pure user names of IPoX or pppoe users.";
      list include-type {
        key "type";
        min-elements "1";
        ordered-by user;
        description
          "Configure the creation mode for the pure user names of IPoX or pppoe users.";
        uses include-type-group;
      }
    }
  }
  grouping default-user-name-template {
    description
      "Configure a user name template to a Broadband Access Server (BAS) interface.";
    container default-user-name-template {
      description
        "Configure a user name template to a Broadband Access Server (BAS) interface.";
      leaf name {
        type leafref {
          path "/bras-user-manage:bras-user-manage/bras-user-manage:default-user-name-templates/bras-user-manage:default-user-name-template/bras-user-manage:template-name";
        }
        description
          "Specifies a user name template.";
      }
    }
  }
  grouping ip-user-log-statistic {
    description
      "Operation data of user log statistics grouping.";
    container statistic {
      config false;
      description
        "Operation data of user log statistics.";
      leaf bind-ssl-policy {
        type string {
          length "1..23";
        }
        description
          "SSL policy name.";
      }
      leaf ssl-status {
        type enumeration {
          enum "init" {
            value 0;
            description
              "SSL init status.";
          }
          enum "connecting" {
            value 1;
            description
              "SSL connecting status.";
          }
          enum "connected" {
            value 2;
            description
              "SSL connected status.";
          }
        }
        description
          "SSL status.";
      }
    }
  }
  grouping ip-user-log-cu-statistic {
    description
      "Operation data of user log statistics grouping.";
    container cu-statistics {
      config false;
      description
        "List of cu user log statistics.";
      list cu-statistic {
        key "upmng-instance";
        description
          "Operation data of cu user log statistics.";
        leaf upmng-instance {
          type string {
            length "1..15";
          }
          description
            "The name of UPMNG instance.";
        }
        leaf bind-ssl-policy {
          type string {
            length "1..23";
          }
          description
            "SSL policy name.";
        }
        leaf ssl-status {
          type enumeration {
            enum "init" {
              value 0;
              description
                "SSL init status.";
            }
            enum "connecting" {
              value 1;
              description
                "SSL connecting status.";
            }
            enum "connected" {
              value 2;
              description
                "SSL connected status.";
            }
          }
          description
            "SSL status.";
        }
      }
    }
  }
  grouping online-fail-or-offline-statistic-info {
    description
      "Operation data of user online failed or offline record statistics grouping.";
    leaf record-type {
      type enumeration {
        enum "online-fail-record" {
          value 2;
          description
            "User login failure records.";
        }
        enum "offline-record" {
          value 1;
          description
            "User logout records.";
        }
      }
      description
        "Display user login failure or logout records.";
    }
    leaf record-order {
      type enumeration {
        enum "mac-address" {
          value 1;
          description
            "Display user login failure/logout records based on MAC addresses.";
        }
        enum "link-info" {
          value 2;
          description
            "Display user login failure/logout records based on interface IDs+VLAN IDs.";
        }
      }
      description
        "Display user login failure/logout records based on MAC addresses or interface IDs+VLAN IDs.";
    }
    leaf top-number {
      type uint8 {
        range "1..50";
      }
      description
        "Sequence number. The number of login failure/logout records are listed in descending order.";
    }
    leaf hour {
      type uint32 {
        range "0..23";
      }
      units h;
      description
        "Display user login failure/logout records generated within a specified period of hour.";
      ext:support-filter "true";
    }
    leaf minute {
      type uint32 {
        range "0..59";
      }
      units min;
      description
        "Display user login failure/logout records generated within a specified period of minute.";
      ext:support-filter "true";
    }
    leaf second {
      type uint32 {
        range "0..59";
      }
      units s;
      description
        "Display user login failure/logout records generated within a specified period of second.";
      ext:support-filter "true";
    }
    leaf interface {
      type string {
        length "1..63";
      }
      description
        "Interface through which users fail to go online or go offline.";
    }
    leaf pevlan {
      type uint16;
      description
        "Outer VLAN ID.";
    }
    leaf cevlan {
      type uint16;
      description
        "Inner VLAN ID.";
    }
    leaf mac {
      type pub-type:mac-address;
      description
        "MAC address.";
    }
    leaf times {
      type uint32;
      description
        "Number of login failure/logout records.";
    }
  }
  container bras-user-manage {
    description
      "Bras user management data model define.";
    container service-identify-policys {
      description
        "List of the service identification policy and enter the service identification policy.";
      list service-identify-policy {
        key "name";
        description
          "Configure a service identification policy and enter the service identification policy.";
        leaf name {
          type string {
            length "1..32";
            pattern "[a-z0-9._-]{1,32}";
          }
          must "../name != '-' and ../name != '--'";
          description
            "Specifies the name of a service identification policy.";
          ext:case-sensitivity lower-only;
        }
        container mode {
          description
            "Configure the service identification mode.";
          leaf mode {
            type bras-user-manage-service-identify-type;
            description
              "Configures the service identification mode.";
          }
        }
        container dhcp-option60 {
          when "../mode/mode='dhcp-option60'";
          description
            "Configure option60 attribute.";
          uses option60-vendorclass-cfg;
        }
        container vendor-class {
          when "../mode/mode='vendor-class'";
          description
            "Configure vendor-class attribute.";   
          uses option60-vendorclass-cfg;
        }
        container dscp-domain-mappings {
          when "../mode/mode='dscp'";
          description
            "List of the mapping between packets with the specified DSCP value and domains.";
          list dscp-domain-mapping {
            key "start-dscp-id";
            description
              "Configure the mapping between packets with the specified DSCP value and domains.";
            leaf start-dscp-id {
              type uint16 {
                range "0..63";
              }
              description
                "Specifies the start DSCP ID.";
            }
            leaf end-dscp-id {
              type uint16 {
                range "0..63";
              }
              must "../end-dscp-id >= ../start-dscp-id";
              ext:dynamic-default {
                ext:default-value "../start-dscp-id" {
                description "The default value is equal to start DSCP ID.";
                }
              }
              description
                "Specifies the end DSCP ID.";
            }
            leaf domain {
              type leafref {
                path "/aaa:aaa/aaa:domains/aaa:domain/aaa:name";
              }
              mandatory true;
              description
                "Specifies the domain name.";
            }
          }
        }
        container priority-8021p-domain-mappings {
          when "../mode/mode='service8021p-innervlan' or ../mode/mode='service8021p-outervlan'";
          description
            "List of the mapping between 802.1p value of packets and domains.";
          list priority-8021p-domain-mapping {
            key "start-8021p-num";
            description
              "Configure the mapping between 802.1p value of packets and domains.";
            leaf start-8021p-num {
              type uint16 {
                range "0..7";
              }
              description
                "Specifies the start 8021p value.";
            }
            leaf end-8021p-num {
              type uint16 {
                range "0..7";
              }
              must "../end-8021p-num >= ../start-8021p-num";
              ext:dynamic-default {
                ext:default-value "../start-8021p-num" {
                description "The default value is equal to start 8021p value.";
                }
              }
              description
                "Specifies the end 8021p value.";
            }
            leaf domain {
              type leafref {
                path "/aaa:aaa/aaa:domains/aaa:domain/aaa:name";
              }
              mandatory true;
              description
                "Specifies the domain name.";
            }
          }
        }
      }
    }
    container domain-map-lists {
      description
        "List of the domain map.";
      list domain-map-list {
        key "name";
        max-elements 4;
        description
          "Configure a domain mapping list.";
        leaf name {
          type string {
            length "1..32";
            pattern "[!-~]{1,32}";
            pattern "([^A-Z\"']{1,32})";
          }
          must "../name != '-' and ../name != '--'";
          description
            "Domain map list name.";
          ext:case-sensitivity lower-only;
        }
        container domain-mappings {
          description
            "List of the domain mappings in the domain mapping list.";
          list domain-mapping {
            key "source-domain";
            max-elements 128;
            description
              "Configure a domain mapping in the domain mapping list.";
            leaf source-domain {
              type leafref {
                path "/aaa:aaa/aaa:domains/aaa:domain/aaa:name";
              }
              description
                "Source domain name.";
            }
            leaf destination-domain {
              type leafref {
                path "/aaa:aaa/aaa:domains/aaa:domain/aaa:name";
              }
              mandatory true;
              description
                "Destination domain name.";
            }
            leaf extend {
              type boolean;
              default "false";
              description
                "Enable/disable extending mapping.";
            }
          }
        }
      }
    }
    container domain-lists {
      description
        "List of the domain.";
      list domain-list {
        key "name";
        max-elements 128;
        description
          "Configure a domain list.";
        leaf name {
          type string {
            length "1..32";
            pattern "[!-~]{1,32}";
            pattern "([^A-Z\"%'*/:<>\\?@|]{1,32})";
          }
          must "../name != '-' and ../name != '--'";
          description
            "Domain list name.";
          ext:case-sensitivity lower-only;
        }
        leaf-list domain-list-domain {
          type leafref {
            path "/aaa:aaa/aaa:domains/aaa:domain/aaa:name";
          }
          max-elements 16384;
          description
            "Configure a domain to a domain list when the same operation needs to be performed for the domains.";
        }
      }
    }
    container ip-userlog {
      must "((ip-userlog-access/ip-address and ip-userlog-call-status/ip-address and
         ip-userlog-access/udp-port and ip-userlog-call-status/udp-port) and
        (((ip-userlog-access/ip-address=ip-userlog-call-status/ip-address) and
         (ip-userlog-access/udp-port=ip-userlog-call-status/udp-port) and
         (ip-userlog-access/transport-mode=ip-userlog-call-status/transport-mode)) or
        (ip-userlog-access/ip-address!=ip-userlog-call-status/ip-address) or
        (ip-userlog-access/udp-port!=ip-userlog-call-status/udp-port))) or
        not(ip-userlog-access/ip-address and ip-userlog-call-status/ip-address and
         ip-userlog-access/udp-port and ip-userlog-call-status/udp-port)";
      presence "ip-userlog";
      description
        "Configure the Network Devices to generate user login and logout logs and send the logs to a log server.";
      container ip-userlog-access {
        description
          "Configure user login and logout logs.";
        leaf ip-address {
          type inet:ipv4-address-no-zone;
          description
            "Sets an IP address for a log server.";
        }
        leaf udp-port {
          when "../ip-address";
          type uint32 {
            range "1..65535";
          }
          mandatory true;
          description
            "Sets a UDP port number for a log server.";
        }
        leaf transport-mode {
          when "../ip-address";
          type bras-user-manage-userlog-transport-mode-type;
          default "udp";
          description
            "Sets a transport mode for a log server.";
        }
        leaf version {
          type uint32 {
            range "1..4";
          }
          description
            "Specifies the version of packets used to send user login and logout logs.";
        }
        leaf enable {
          when "../ip-address and ../version";
          type boolean;
          default "false";
          description
            "Enable/disable the Network Devices to generate user login and logout logs and send the logs to a log server.";
        }
        leaf send-format-syslog {
          type boolean;
          default "false";
          description
            "Enable/disable the device to use the syslog format to send user online and offline logs.";
        }
        uses ip-user-log-statistic;
        uses ip-user-log-cu-statistic;
      }
      container ip-userlog-call-status {
        description
          "Configure user online result logs.";
        leaf ip-address {
          type inet:ipv4-address-no-zone;
          description
            "Sets calling status log ip.";
        }
        leaf udp-port {
          when "../ip-address";
          type uint32 {
            range "1..65535";
          }
          mandatory true;
          description
            "Sets user calling status log port.";
        }
        leaf transport-mode {
          when "../ip-address";
          type bras-user-manage-userlog-transport-mode-type;
          default "udp";
          description
            "Sets a transport mode for a log server.";
        }
        leaf call-status-enable {
          type boolean;
          default "false";
          description
            "Enable/disable the user calling status log information.";
        }
        uses ip-user-log-statistic;
        uses ip-user-log-cu-statistic;
      }
      container ip-userlog-ssl-policys {
        description
          "List of SSL policy of user login and logout logs.";
        list ip-userlog-ssl-policy {
          key "ip-address port";
          max-elements "2";
          description
            "Configure SSL policy of user login and logout logs.";
          leaf ip-address {
            type inet:ipv4-address-no-zone;
            description
              "Sets user log server ip.";
          }
          leaf port {
            type uint16 {
              range "1..65535";
            }
            description
              "Sets user log server port.";
          }
          leaf ssl-policy-name {
            type leafref {
              path "/ssl:ssl/ssl:ssl-policys/ssl:ssl-policy/ssl:policy-name";
            }
            mandatory true;
            description
              "The name of SSL policy.";
          }
        }
      }
    }
    container trace {
      description
        "Configure service trace.";
      leaf online-fail-auto-enable {
        type boolean;
        default "true";
        description
          "Enable/disable the automatic service trace function.";
      }
    }
    container user-authorization {
      description
        "Configure the user authorization.";
      leaf reauthorize-enable {
        type boolean;
        default "false";
        description
          "Enable/disable command-line reauthorization.";
      }
    }
    container qoe-accounting {
      description
        "Configure a QoE accounting copy server.";
      leaf radius-server-group-name {
        type leafref {
          path "/radius:radius/radius:radius-server-groups/radius:radius-server-group/radius:name";
        }
        description
          "Configure a QoE accounting copy server.";
      }
      leaf interval {
        type uint32 {
          range "30..1440";
        }
        units min;
        description
          "Configure a real-time accounting interval for the QoE.";
      }
    }
    container access-policy {
      description
        "Configure a policy of users are allowed or to go online.";
      leaf pure-user-name-no-exist-online {
        type boolean;
        default "false";
        description
          "Enable/disable users are allowed to go online if the pure user name is empty.";
      }
    }
    container realtime-accounting-backup {
      description
        "Configure a real-time accounting backup between the master and slave MPUs.";
      leaf enable {
        type boolean;
        default "false";
        description
          "Enable/disable real-time accounting backup between the master and slave MPUs. By default, real-time accounting backup is disabled between the master and slave MPUs. After a master/slave MPU switchover, the real-time accounting interval is reset.";
      }
    }
    container accounting-time-calibration {
      description
        "Configure accounting time calibration for PPPoE users.";
      leaf enable {
        type boolean;
        default "true";
        description
          "Enable/disable accounting time calibration for PPPoE users.";
      }
    }
    container acct-session-id {
      description
        "Configure the version for generating the accounting session ID.";
      leaf version {
        type enumeration {
          enum "version1" {
            value 1;
            description
              "Indicates that the accounting session ID of the user is generated by version 1.";
          }
          enum "version2" {
            value 2;
            description
              "Indicates that the accounting session ID of the user is generated by version 2.";
          }
          enum "version3" {
            value 3;
            description
              "Indicates that the accounting session ID of the user is generated by version 3.";
          }
          enum "version4" {
            value 4;
            description
              "Indicates that the accounting session ID of the user is generated by version 4.";
          }
          enum "version5" {
            value 5;
            description
              "Indicates that the accounting session ID of the user is generated by version 5.";
          }
          enum "version6" {
            value 6;
            description
              "Indicates that the accounting session ID of the user is generated by version 6.";
          }
        }
        default "version1";
        description
          "Sets the version for generating the accounting session ID.";
      }
      leaf nas-logic-sysname {
        when "../version='version1' or ../version='version4' or ../version='version5'";
        type string {
          length "1..7";
        }
        description
          "Indicates the host name which is used to generate accounting session ID of the user.";
      }
    }
    container access-speed {
      description
        "Configure the user access speed.";
      container adjust-system-state {
        description
          "Configure the Network Devices to adjust the user access rate based on the system status.";
        leaf enable {
          type boolean;
          default "true";
          description
            "Enable/disable the user access rate according to the cpu state.";
        }
      }
      container access-rate-limitation {
        must "(access-number and access-period) or (not(access-number) and not(access-period))";
        description
          "Configure the access rate limitation on the Network Devices. By default, users access the device at a lower rate between that limited by the CPU usage and that limited by the memory usage.";
        leaf access-number {
          type uint32 {
            range "1..65535";
          }
          description
            "Specifies the number of access users during the statistics period.";
        }
        leaf access-period {
          type uint32 {
            range "1..65535";
          }
          units s;
          description
            "Specifies the period of access user statistics.";
        }
        leaf type {
          when "../access-number and ../access-period";
          type enumeration {
            enum "forced" {
            value 1;
            description
              "Indicates that users access the device at the configured access rate, regardless of the CPU or memory usage.";
            }
            enum "level1" {
            value 2;
            description
              "Indicates that the router adjusts the user access rate based on the system status.";
            }
            enum "level2" {
            value 3;
            description
              "Indicates that the router reduces the memory limit on the user access rate.";
            }
          }
          description
            "Sets the access rate limitation type.";
        }
        leaf trigger-packet-enable {
          type boolean;
          default "true";
          description
            "Enable/disable a device to adjust the access rate of users who go online by sending ARP/IP/IPv6/ND packets based on the system status.";
        }
      }
      container access-queue-threshold {
        description
          "Configure a size threshold for the UM message queue to control the usage of the UM message queue. When the usage of the UM message queue reaches the threshold, the system decreases or increases the CPCAR value.";
        leaf msg-queue-length {
          type uint32 {
            range "1..48";
          }
          default "24";
          description
            "Set a size threshold for the access queue.";
        }
      }
      container offline-speed {
        description
          "Configure the user offline speed, specifically, the number of users that go offline within a second. If the number of users to go offline within a second exceeds the configured value, the users that cannot go offline enter the offline queue.";
        leaf offline-number {
          type uint32 {
            range "50..256";
          }
          default "256";
          description
            "Specifies the number of users that go offline within a second.";
        }
      }
    }
    container access-speed-cu {
      description
        "Configure the user access speed for CU.";
      container adjustment-system-state {
        must "./queue-deep-alarm-threshold > ./queue-deep-resume-threshold";
        description
          "Configure the user access speed for CU.";
        leaf check-enable {
          type boolean;
          default "true";
          description
            "Enable/disable avalanche avoidance.";
        }
        leaf interval {
          type uint32 {
            range "1..60";
          }
          units s;
          default "1";
          description
            "Set the interval at which the access speed is adjusted.";
        }
        leaf delay-count {
          type uint32 {
            range "1..300";
          }
          default "2";
          description
            "Set the number of recovery delays.";
        }
        leaf queue-deep-alarm-threshold {
          type uint32 {
            range "1..100";
          }
          default "3";
          description
            "Specifies a CUSP queue depth usage threshold for restoring the user access rate.";
        }
        leaf queue-deep-resume-threshold {
          type uint32 {
            range "1..100";
          }
          default "2";
          description
            "Specifies a CUSP queue depth usage threshold for decreasing the user access rate.";
        }
      }
      container adjustment-user-type {
        description
          "Configure dynamic user access speed adjustment based on the control channel status for specified user types.";
        leaf dhcp-enable {
          type boolean;
          default "true";
          description
            "Enable/disable the DHCP switch.";
        }
        leaf pppoe-enable {
          type boolean;
          default "true";
          description
            "Enable/disable the PPPoE switch.";
        }
        leaf ipv4-trigger-enable {
          type boolean;
          default "true";
          description
            "Enable/disable the IPv4 trigger switch.";
        }
        leaf ipv6-trigger-enable {
          type boolean;
          default "true";
          description
            "Enable/disable the IPv6 trigger switch.";
        }
        leaf l2tp-enable {
          type boolean;
          default "true";
          description
            "Enable/disable the L2TP switch.";
        }
        leaf dhcpv6-enable {
          type boolean;
          default "true";
          description
            "Enable/disable the DHCPv6 switch.";
        }
      }
    }
    container default-password-templates {
      description
        "List of IPoX user passwords.";
      list default-password-template {
        key "template-name";
        description
          "Configure the password of an IPoX user.";
        leaf template-name {
          type string {
            length "1..31";
          }
          description
            "Specifies the name of the template used to determine the user password generation mode.";
        }
        uses default-password;
      }
    }
    container access-trigger-loose {
      description
        "Configure online in loose mode after the system restarts due to an exception reduces client restarts.";
      leaf loose-time {
        when "../all-time='false'";
        type uint32 {
          range "0..1440";
        }
        units min;
        default "120";
        description
          "Period during which users can get online in loose mode after the system restarts. 0 indicates that users cannot get online in loose mode after the system restarts.";
      }
      leaf all-time {
        type boolean;
        default "false";
        description
          "Enable/disable loose mode for getting online after the system restarts.";
      }
      leaf infinite-lease {
        type boolean;
        default "false";
        description
          "Enable/disable infiniting lease users can get online in loose mode after the system restarts.";
      }
    }
    container local-aaa-server-users {
      description
        "List of the local AAA server users.";
      list local-aaa-server-user {
        key "user-name";
        description
          "Configure a local AAA server user.";
        leaf user-name {
          type string {
            length "1..253";
            pattern "([^A-Z\"*?]{1,253})";
          }
          description
            "Name of a local user. The minimum length of a username is determined by user-name-min-len and security-policy. If security-policy is set to false and user-name-min-len is configured, the configuration takes effect. When security-policy is set to true, the minimum length of the username must be at least 6 characters. If user-name-min-len is configured and the user-name-min-len value is greater than 6 characters, the minimum length of the username is equal to the user-name-min-len value. If security-policy is set to false and user-name-min-len is not configured, the minimum length of the username is 1. If the username contains more than 32 characters, service-snmp cannot be set to true. If the username contains more than 32 characters, service-snmp cannot be set to true. You can add a domain name delimiter for the username. The default value is (@). The following characters are (\\), (/), (:), (<), (>), (|), (@), ('), (%). At most one domain name delimiter can be used, and a character must exist before and after the domain name delimiter. The username (including the domain name delimiter) that already exists may be configured as another supported domain name delimiter.";
          ext:case-sensitivity lower-only;
        }
        leaf password-type {
          type enumeration {
            enum "cipher-password" {
              value 1;
              description
                "Specifies a ciphertext password, the new password is at least eight characters long and contains at least two of upper-case letters, lower-case letters, digits, and special characters.";
            }
            enum "irreversible-password" {
              value 2;
              description
                "Specifies an irreversible password.";
            }
          }
          mandatory true;
          description
            "Specifies the password type of a user.";
        }
        leaf password {
          type pub-type:password-extend;
          mandatory true;
          description
            "Specifies the password of a user.";
        }
        leaf user-state {
          type enumeration {
            enum "block" {
              value 0;
              description
                "Indicates that a user is in the blocked state. The device denies any authentication request from a blocked user.";
            }
            enum "active" {
              value 1;
              description
                "Indicates that a user is in the active state. The device receives and handles the authentication request from an active user.";
            }
            enum "lock-when-authen-fail" {
              value 2;
              description
                "Indicates that a user is locked due to authentication failures. When the number of consecutive authentication failures of a user reaches the limit, the user is locked. The device denies any authentication request from a locked users within the specified time.";
            }
          }
          default "lock-when-authen-fail";
          description
            "Specifies the state of a user.";
        }
        leaf user-level {
          type uint16 {
            range "0..15";
          }
          description
            "Specifies the level of a user. If the command level adjustment function is disabled, the value of userLevel ranges from 0 to 3. If the command level adjustment function is enabled, the value of userLevel ranges from 0 to 15.";
        }
        leaf ftp-directory {
          type string {
            length "1..255";
          }
          description
            "Specifies an FTP path.";
        }
        leaf idle-cut {
          type boolean;
          default "false";
          description
            "Enable/disable the idle-cut function.";
        }
        leaf fail-times {
          when "../user-state='lock-when-authen-fail'";
          type uint32 {
            range "1..10";
          }
          default "3";
          description
            "Specifies the maximum number of allowed authentication failures. When the number of consecutive authentication failures of a user reaches the limit, the user is locked.";
        }
        leaf fail-interval {
          when "../user-state='lock-when-authen-fail'";
          type uint32 {
            range "1..65535";
          }
          units min;
          default "5";
          description
            "Specifies the interval at which a locked user is performed to be re-authenticated.";
        }
        leaf callback-nocheck {
          type boolean;
          default "false";
          description
            "Enable/disable the callback signals of a modem are not checked.";
        }
        leaf callback-number {
          type string {
            length "1..64";
          }
          description
            "Specifies a string of characters for callback user dial-up.";
        }
        leaf qos-profile-name {
          type leafref {
            path "/qos:qos/qos:queue-scheduler-template/qos:profiles/qos:profile/qos:name";
          }
          must "/qos:qos/qos:queue-scheduler-template/qos:profiles/qos:profile[qos:name=current()]/qos:mode='normal'";
          description
            "Specifies the name of the QoS profile.";
        }
        leaf ip-address {
          type inet:ipv4-address-no-zone;
          description
            "Specifies the IP address of a local user account, the IP address must be configured in the ip pool when it is not disabled or it belongs to the address segment of excluded-ip-address.";
        }
        leaf vpn-name {
          when "../ip-address";
          type leafref {
            path "/ni:network-instance/ni:instances/ni:instance/ni:name";
          }
          must "/ni:network-instance/ni:instances/ni:instance[ni:name=current()]/l3vpn:afs/l3vpn:af[l3vpn:type='ipv4-unicast']";
          description
            "Specifies a VPN name, when the vpn-name is not delivered, the ip pool is matched based on the ip-address. When vpn-name is delivered, ip-address and vpn-name must be matched to match the ip pool.";
        }
        leaf user-group-name {
          type leafref {
            path "/aaa:aaa/aaa:user-groups/aaa:user-group/aaa:name";
          }
          description
            "Specifies the name of a user group.";
        }
        leaf terminal {
          type boolean;
          default "false";
          description
            "Enable/disable login using a terminal.";
        }
        leaf telnet {
          type boolean;
          default "false";
          description
            "Enable/disable login using Telnet.";
        }
        leaf ftp {
          type boolean;
          default "false";
          description
            "Enable/disable login using FTP.";
        }
        leaf ppp {
          type boolean;
          default "false";
          description
            "Enable/disable login using PPP.";
        }
        leaf ssh {
          type boolean;
          default "false";
          description
            "Enable/disable login using SSH.";
        }
        leaf vlan-web {
          type boolean;
          default "false";
          description
            "Enable/disable login using VLANWeb.";
        }
        leaf vlan {
          type boolean;
          default "false";
          description
            "Enable/disable login using VLANBinding.";
        }
        leaf dot1x {
          type boolean;
          default "false";
          description
            "Enable/disable login through DOT1X.";
        }
        leaf x25-pad {
          type boolean;
          default "false";
          description
            "Enable/disable login through x25Pad.";
        }
        leaf tunnel {
          type boolean;
          default "false";
          description
            "Enable/disable login through tunnel.";
        }
        leaf snmp {
          type boolean;
          default "false";
          description
            "Enable/disable login using SNMP.";
        }
        leaf mml {
          type boolean;
          default "false";
          description
            "Enable/disable login using MML.";
        }
        leaf qx {
          type boolean;
          default "false";
          description
            "Enable/disable login using QX.";
        }
        leaf http {
          type boolean;
          default "false";
          description
            "Enable/disable login using HTTP.";
        }
        leaf expire-time {
          type pub-type:date;
          description
            "The expiration time must be later the current date but within the year 2099 (included).";
        }
      }
    }
    container family-or-common-user {
      description
        "Configure whether to switch family users to common users in an AAA domain. By default, after the user-max-session command is run in an AAA domain, users with the same user name in the domain are family users.";
      leaf user-no-family-max-session {
        type enumeration {
          enum "same-user-name-limit" {
            value 1;
            description
              "If the user-max-session command has been run in an AAA domain. you can run the user no-family user-max-session all command to limit the number of users with the same user name in the domain instead of switching users with the same user name to family users.";
          }
          enum "family-to-common-user" {
            value 2;
            description
              "Switches family users to common users, The user-max-session max-session-number command must be run in the AAA domain and max-session-number must be set to 1 for the user no-family user-max-session 1 command to take effect.";
          }
        }
        description
          "Determines whether to switch family users to common users in an AAA domain.";
      }
    }
    container user-warning-threshold {
      must "not(user-warning-threshold-upper-limit) or not(user-warning-threshold-lower-limit) or user-warning-threshold-upper-limit >= user-warning-threshold-lower-limit";
      description
        "Configure monitor and maintain.";
      leaf slot-warning-threshold {
        type uint32 {
          range "1..100";
        }
        units %;
        default "100";
        description
          "Sets an alarm threshold for users allowed to access an interface board. If the percentage of users currently accessing the interface board reaches the threshold, an alarm is generated on the device.";
      }
      leaf user-warning-threshold-upper-limit {
        type uint32 {
          range "1..100";
        }
        units %;
        description
          "Specifies an upper threshold for the number of users.";
      }
      leaf user-warning-threshold-lower-limit {
        type uint32 {
          range "0..99";
        }
        units %;
        description
          "Specifies a lower threshold for the number of users.";
      }
    }
    container user-resource-exhaust-alarm {
      must "main-resource-usage-upper-limit > main-resource-usage-lower-limit";
      must "slot-resource-usage-upper-limit > slot-resource-usage-lower-limit";
      must "main-cpu-usage-upper-limit > main-cpu-usage-lower-limit";
      must "slot-cpu-usage-upper-limit > slot-cpu-usage-lower-limit";
      description
        "Configure the system to generate an alarm when the user resource or CPU usage reaches an alarm threshold and to generate a clear alarm when the user resource or CPU usage falls below a clear alarm threshold.";
      leaf user-resource-exhaust-threshold {
        type boolean;
        default "false";
        description
          "Enable/disable the resource exhaust alarm function for online user resource.";
      }
      leaf main-resource-usage-upper-limit {
        type uint8 {
          range "1..100";
        }
        units %;
        default "85";
        description
          "The upper-limit value of main-resource-usage.";
      }
      leaf main-resource-usage-lower-limit {
        type uint8 {
          range "1..100";
        }
        units %;
        default "75";
        description
          "The lower-limit value of main-resource-usage.";
      }
      leaf slot-resource-usage-upper-limit {
        type uint8 {
          range "1..100";
        }
        units %;
        default "85";
        description
          "The upper-limit value of slot-resource-usage.";
      }
      leaf slot-resource-usage-lower-limit {
        type uint8 {
          range "1..100";
        }
        units %;
        default "75";
        description
          "The lower-limit value of slot-resource-usage.";
      }
      leaf main-cpu-usage-upper-limit {
        type uint8 {
          range "1..100";
        }
        units %;
        default "85";
        description
          "The upper-limit value of main-cpu-usage.";
      }
      leaf main-cpu-usage-lower-limit {
        type uint8 {
          range "1..100";
        }
        units %;
        default "75";
        description
          "The lower-limit value of main-cpu-usage.";
      }
      leaf slot-cpu-usage-upper-limit {
        type uint8 {
          range "1..100";
        }
        units %;
        default "85";
        description
          "The upper-limit value of slot-cpu-usage.";
      }
      leaf slot-cpu-usage-lower-limit {
        type uint8 {
          range "1..100";
        }
        units %;
        default "75";
        description
          "The lower-limit value of slot-cpu-usage.";
      }
    }
    container access-backup-trap-usernums {
      description
        "List of minor and major alarm thresholds for the number of users configured on an interface during backup detections.";
      list access-backup-trap-usernum {
        must "minor-trap-usernum <= major-trap-usernum";
        key "interface-type";
        description
          "Configure minor and major alarm thresholds for the number of users configured on an interface during backup detections.";
        leaf interface-type {
          type enumeration {
            enum "eth-trunk" {
              value 1;
              description
                "Eth-Trunk interface type.";
            }
            enum "gigabit-ethernet" {
              value 2;
              description
                "GigabitEthernet interface type.";
            }
            enum "gigabit-ethernet-10-ge" {
              value 3;
              description
                "GigabitEthernet10GE interface type.";
            }
            enum "gigabit-ethernet-100-ge" {
              value 4;
              description
                "GigabitEthernet100GE interface type.";
            }
            enum "gigabit-ethernet-25-ge" {
              value 5;
              description
                "GigabitEthernet25GE interface type.";
            }
            enum "gigabit-ethernet-50-ge" {
              value 6;
              description
                "GigabitEthernet50GE interface type.";
            }
            enum "gigabit-ethernet-50-or-100-ge" {
              value 7;
              description
                "GigabitEthernet50GE or GigabitEthernet100GE interface type.";
            }
            enum "xgigabit-ethernet" {
              value 8;
              description
                "XGigabitEthernet interface type.";
            }
          }
          description
            "Type of an interface.";
        }
        leaf minor-trap-usernum {
          type uint16 {
            range "1..65535";
          }
          default "1000";
          description
            "Minor alarm threshold for the number of users.";
        }
        leaf major-trap-usernum {
          type uint16 {
            range "1..65535";
          }
          default "10000";
          description
            "Major alarm threshold for the number of users.";
        }
      }
    }
    container access-backup-check-detect {
      must "detect-count >= fail-count";
      description
        "Configure backup detection interval and number of backup detections on a BAS interface.";
      leaf detect-interval {
        type uint8 {
          range "0..24";
        }
        units h;
        default "8";
        description
          "Detection interval.";
      }
      leaf detect-count {
        type uint8 {
          range "1..255";
        }
        default "21";
        description
          "Total number of detections in a detection period.";
      }
      leaf fail-count {
        type uint8 {
          range "1..255";
        }
        default "14";
        description
          "Threshold for the number of detection failures over which an alarm is generated.";
      }
    }
    container local-bill {
      presence "local-bill";
      description
        "Configure the local bill.";
      leaf bill-backup-server-ip {
        type inet:ipv4-address-no-zone;
        description
          "Specifies the IP address of a bill server.";
      }
      leaf bill-backup-file-name {
        when "../bill-backup-server-ip";
        type string {
          length "1..30";
        }
        mandatory true;
        description
          "Specifies a file used to store bills on a bill server.";
      }
      leaf bill-backup-user-name {
        when "../bill-backup-server-ip";
        type string {
          length "1..64";
        }
        description
          "Sets a user name used to set up an SFTP session with a bill server.";
      }
      leaf bill-backup-password {
        when "../bill-backup-user-name";
        type pub-type:password-extend {
          length "1..128";
        }
        mandatory true;
        description
          "Sets a password used to set up an SFTP session with a bill server. The password is a string ranging from 1 to 16 characters for a simple password and 1 to 128 characters for a ciphertext password.";
      }
      leaf bill-backup-port-number {
        when "../bill-backup-user-name";
        type uint32 {
          range "1..65535";
        }
        mandatory true;
        description
          "Sets a port number used to set up an SFTP session with a bill server.";
      }
      leaf local-bill-pool-enable {
        type boolean;
        default "false";
        description
          "Enable/disable a local bill pool.";
      }
      leaf cache-backup-interval {
        type uint32 {
          range "1..65535";
        }
        units min;
        default "1440";
        description
          "Sets an interval for automatic local bill transfer from the local bill pool to a bill server.";
      }
      leaf cache-alarm-threshold {
        type uint32 {
          range "50..100";
        }
        units %;
        default "75";
        description
          "Sets a bill alarm threshold for the usage of the local bill pool.";
      }
      leaf cache-backup-mode {
        type enumeration {
          enum "none" {
            value 1;
            description
              "No bill backup.";
          }
          enum "tftp" {
            value 2;
            description
              "To backup bills to bill server by tftp.";
          }
          enum "cfcard" {
            value 3;
            description
              "Cfcard.";
          }
          enum "sftp" {
            value 5;
            description
              "To backup bills to bill server by sftp.";
          }
        }
        default "cfcard";
        description
          "Configures the transfer mode for bills in the local bill pool.";
      }
      leaf cfcard-backup-interval {
        type uint32 {
          range "1..65535";
        }
        units min;
        default "1440";
        description
          "Sets an interval for automatic local bill transfer from the CF card to a bill server.";
      }
      leaf cfcard-alarm-threshold {
        type uint32 {
          range "50..100";
        }
        units min;
        default "75";
        description
          "Sets a bill alarm threshold for the usage of the CF card.";
      }
      leaf cfcard-backup-mode {
        type enumeration {
          enum "tftp" {
            value 2;
            description
              "To backup bills to bill server by tftp.";
          }
          enum "sftp" {
            value 5;
            description
              "To backup bills to bill server by sftp.";
          }
        }
        default "sftp";
        description
          "Configures a mode in which bills in the CF card are transferred to a bill server.";
      }
    }
    container access-user-specification {
      description
        "Configure the user specification mode.";
      leaf spec-mode {
        type enumeration {
          enum "dual-stack-expand" {
            value 1;
            description
              "Indicates that the user specification mode is dual-stack expansion.";
          }
        }
        description
          "The mode of user specification.";
      }
    }
    container access-services {
      description
        "List of the access service templates.";
      list access-service {
        key "name";
        description
          "Configure an access service template.";
        leaf name {
          type string {
            length "1..32";
            pattern "[!-~]{1,32}";
            pattern "([^A-Z\"%'*/:<>\\?@|]{1,32})";
          }
          must "../name != '-' and ../name != '--'";
          description
            "Access service name.";
          ext:case-sensitivity lower-only;
        }
        container qos-profile {
          description
            "Configure the QoS profile bound to an access service template.";
          leaf qos-profile-name {
            type leafref {
              path "/qos:qos/qos:queue-scheduler-template/qos:profiles/qos:profile/qos:name";
            }
            must "/qos:qos/qos:queue-scheduler-template/qos:profiles/qos:profile[qos:name=current()]/qos:mode='normal'";
            description
              "Specifies the name of a bound QoS profile.";
          }
        }
        container qos-profile-time-ranges {
          description
            "List of the QoS profile containing a time segment bound to an access service template.";
          list qos-profile-time-range {
            key "time-range-name";
            max-elements 16;
            description
              "Configure the QoS profile containing a time segment bound to an access service template.";
            leaf time-range-name {
              type leafref {
                path "/timerange:time-range/timerange:time-range-instances/timerange:time-range-instance/timerange:name";
              }
              description
                "Specifies the name of a time range.";
            }
            leaf qos-profile-name {
              type leafref {
                path "/qos:qos/qos:queue-scheduler-template/qos:profiles/qos:profile/qos:name";
              }
              must "/qos:qos/qos:queue-scheduler-template/qos:profiles/qos:profile[qos:name=current()]/qos:mode='normal'";
              mandatory true;
              description
                "Specifies the name of a bound QoS profile.";
            }
          }
        }
      }
    }
    container user-policy-interface-down {
      description
        "Configure a policy for online users when an interface goes Down. The policy can be forcibly logging out the users or keeping the users online.";
      leaf user-policy {
        type enumeration {
          enum "offline" {
            value 0;
            description
              "Specifies the policy of forcibly logging out online users when an interface goes Down.";
          }
          enum "online" {
            value 1;
            description
              "Specifies the policy of keeping the users online when an interface goes Down.";
          }
        }
        default "offline";
        description
          "Configures a policy for online users when an interface goes Down. The policy can be forcibly logging out the users or keeping the users online.";
      }
    }
    container up-backup {
      description
        "Configure the UP is faulty or backups.";
      leaf realtime-accounting-enable {
        type boolean;
        default "false";
        description
          "Enable/disable real-time accounting packet sending after the UP is faulty or backed up.";
      }
    }
    container kpi-statistics {
      description
        "Configure functions associated with KPI statistics.";
      leaf user-statistics-enable {
        type boolean;
        default "false";
        description
          "Enable/disable the function of reporting the number of online users by domain, PE-VLAN, or sub-interface. If this KPI is reported by sub-interface, statistics about only PPPoE users are reported.";
      }
    }
    container accounting-copy-groups {
      description
        "List of an accounting copy group and enter the accounting copy group.";
      list accounting-copy-group {
        key "name";
        max-elements "1000";
        description
          "Configure an accounting copy group and enter the accounting copy group.";
        leaf name {
          type string {
            length "1..32";
            pattern "[!-~]{1,32}";
            pattern "([^\"%'*/:<>\\?@|]{1,32})";
          }
          must "../name != '-' and ../name != '--'";
          description
            "Specifies the name of an accounting copy group.";
        }
        container accounting-copy-servers {
          description
            "List of an accounting copy RADIUS server and accounting interval.";
          list accounting-copy-server {
            key "radius-server-group-name";
            max-elements "8";
            description
              "Configure an accounting copy RADIUS server and accounting interval.";
            leaf radius-server-group-name {
              type leafref {
                path "/radius:radius/radius:radius-server-groups/radius:radius-server-group/radius:name";
              }
              description
                "Specifies the name of an accounting copy RADIUS server.";
            }
            leaf accounting-interval {
              type uint32 {
                range "1..65535";
              }
              units min;
              description
                "Specifies the interval of RADIUS server group send accounting packets. If the accounting interval is less than 1 hour, the system pressure may increase, causing the CPU usage to increase.";
            }
          }
        }
      }
    }
    container default-user-name-templates {
      description
        "List of the creation mode for the pure user names of IPoX or pppoe users.";
      list default-user-name-template {
        must "count(../default-user-name-template[template-name!='**default-template**'])<=64";
        key "template-name";
        max-elements "65";
        description
          "Configure the creation mode for the pure user names of IPoX or pppoe users.";
        leaf template-name {
          type string {
            length "1..31";
          }
          description
            "Specifies user template names of users.";
        }
        uses template-default-user-name-group;
      }
    }
    container userlog-with-username {
      description
        "Configure the system to display usernames in the accounting failure logs and the user login and logout logs sent by the log server in cleartext, instead of being anonymized.";
      leaf enable {
        type boolean;
        default "false";
        description
          "Enable/disable the system to display usernames in the accounting failure logs and the user login and logout logs sent by the log server in cleartext, instead of being anonymized.";
      }
    }
    container online-fail-or-offline-records {
      config false;
      description
        "List of the user login failure or logout records.";
      list online-fail-or-offline-record {
        key "record-number record-type";
        config false;
        description
          "Statistics of the user login failure or logout records.";
        leaf record-number {
          type uint64;
          config false;
          description
            "Index of a record.";
        }
        leaf record-type {
          type enumeration {
            enum "offline-record" {
              value 1;
              description
                "Offline record.";
            }
            enum "online-fail-record" {
              value 2;
              description
                "Online fail record.";
            }
          }
          config false;
          description
            "Type of a record.";
        }
        leaf is-normal {
          type boolean;
          config false;
          description
            "User online or offline is normal.";
          ext:support-filter "true";
        }
        leaf interface-name {
          type string {
            length "1..49";
          }
          config false;
          description
            "User access interface.";
          ext:support-filter "true";
        }
        leaf pe-vlan {
          type uint16 {
            range "1..4094";
          }
          config false;
          description
            "Outer VLAN ID of a user.";
          ext:support-filter "true";
        }
        leaf ce-vlan {
          type uint16 {
            range "1..4094";
          }
          config false;
          description
            "Inner VLAN ID of a user.";
          ext:support-filter "true";
        }
        leaf user-name {
          type string {
            length "1..253";
          }
          config false;
          description
            "Name of a user.";
          ext:support-filter "true";
        }
        leaf domain-name {
          type string {
            length "1..64";
          }
          config false;
          description
            "Name of a domain.";
          ext:support-filter "true";
        }
        leaf mac-address {
          type pub-type:mac-address;
          config false;
          description
            "MAC address of a user.";
          ext:support-filter "true";
        }
        leaf user-type {
          type bras-user-manage-all-user-type;
          config false;
          description
            "Type of a user.";
          ext:support-filter "true";
        }
        leaf ipv4-address {
          type inet:ipv4-address-no-zone;
          config false;
          description
            "IPv4 address of a user.";
          ext:support-filter "true";
        }
        leaf ipv6-address {
          type inet:ipv6-address-no-zone;
          config false;
          description
            "IPv6 address of a user.";
          ext:support-filter "true";
        }
        leaf user-id {
          type uint32 {
            range "1..4294967295";
          }
          config false;
          description
            "ID of a user.";
        }
        leaf reason-include {
          type string {
            length "1..256";
          }
          config false;
          description
            "Match the users with the specified string.";
          ext:support-filter "true";
        }
        leaf up-id {
          type uint32 {
            range "1024..2023 | 2048..3047 | 3072..4071 | 4096..5095";
          }
          config false;
          description
            "ID of a vBRAS-UP.";
          ext:support-filter "true";
        }
        leaf access-type {
          type bras-user-manage-user-access-type;
          config false;
          description
            "Type of a user access.";
        }
        leaf stack-type {
          type bras-user-manage-stack-type;
          config false;
          description
            "Whether a user is a dual-stack user.";
        }
        leaf ndra-prefix {
          type inet:ipv6-address-no-zone;
          config false;
          description
            "NDRA prefix of an IPv6 user.";
        }
        leaf ndra-prefix-lenth {
          type uint8 {
            range "0..255";
          }
          config false;
          description
            "Length of the NDRA prefix of an IPv6 user.";
        }
        leaf ipv6-pd-prefix {
          type string {
            length "1..63";
          }
          config false;
          description
            "PD prefix of an IPv6 user.";
        }
        leaf authen-state {
          type bras-user-manage-authen-state;
          config false;
          description
            "Authentication state of a user during login.";
        }
        leaf account-state {
          type bras-user-manage-account-state;
          config false;
          description
            "Accounting state of a user during login.";
        }
        leaf author-state {
          type bras-user-manage-author-state;
          config false;
          description
            "Authorization state of a user during login.";
        }
        leaf login-time {
          type string {
            length "1..49";
          }
          config false;
          description
            "Time when a user goes online.";
        }
        leaf offline-time {
          type string {
            length "1..49";
          }
          config false;
          description
            "Time when a user goes offline.";
        }
        leaf online-fail-or-offline-reason {
          type string {
            length "1..255";
          }
          config false;
          description
            "User logout or login failure reason.";
        }
        leaf reply-message {
          type string {
            length "1..255";
          }
          config false;
          description
            "Reply message from RADIUS server.";
        }
        leaf premapping-reason {
          type string {
            length "1..255";
          }
          config false;
          description
            "Pre-mapping reason.";
        }
        leaf timeout-message {
          type string {
            length "1..255";
          }
          config false;
          description
            "Timeout message of a user.";
        }
        leaf decode-error-attribute {
          type string {
            length "1..255";
          }
          config false;
          description
            "Name of a RADIUS attribute that fails to be parsed during user login.";
        }
        leaf detail-reason {
          type string {
            length "1..255";
          }
          config false;
          description
            "Detailed reason displayed when the HW-Data-Filter attribute fails to be parsed.";
        }
        leaf server-type {
          type bras-user-manage-server-type;
          config false;
          description
            "Type of server.";
        }
        leaf server-group-name {
          type string {
            length 1..32;
          }
          config false;
          description
            "Group name of server.";
        }
        leaf online-fail-or-offline-type-code {
          type uint16;
          config false;
          description
            "Onlinefail or offline type code.";
        }
        leaf view-count {
          type uint32 {
            range "1..131072";
          }
          config false;
          description
            "Display a specified number of last generated user logout or login failure records.";
          ext:support-filter "true";
        }
      }
    }
    container offline-reason-statistics {
      config false;
      description
        "List of the users offline reason.";
      list offline-reason-statistic {
        key "offline-or-online-fail-reason";
        description
          "Statistics of the users offline reason.";
        leaf offline-or-online-fail-reason {
          type int32 {
            range "1..600";
          }
          description
            "Offline or online fail reason.";
        }
        leaf offline-reasons-statistic {
          type int32 {
            range "0..2147483647";
          }
          description
            "The offline reason statistic.";
        }
        leaf online-fail-reason-statistic {
          type int32 {
            range "0..2147483647";
          }
          description
            "The online fail reason statistic.";
        }
      }
    }
    container access-online-number {
      config false;
      description
        "Statistics of the total number of online users based on a specified domain and type.";
      leaf user-type {
        type bras-user-manage-user-online-type;
        config false;
        description
          "Indicates the number of online IPv4 or IPv6 or dual-stack online users.";
        ext:support-filter "true";
      }
      leaf exclude-dual {
        type boolean;
        config false;
        description
          "Indicates the number of online IPv4 users meeting specified conditions.";
        ext:support-filter "true";
      }
      leaf domain-name {
        type string {
          length "1..64";
        }
        config false;
        description
          "Specifies the number of online users who belong to a specified domain.";
        ext:support-filter "true";
      }
      leaf access-type {
        type bras-user-manage-access-type;
        config false;
        description
          "Indicates the number of online users of a specified access type.";
        ext:support-filter "true";
      }
      leaf ipv6-address-protocol {
        type bras-user-manage-ipv6-address-protocol;
        config false;
        description
          "Indicates the number of online users that obtain IPv6 addresses using a specified protocol.";
        ext:support-filter "true";
      }
      leaf ipv6-cpe-mode {
        type bras-user-manage-ipv6-cpe-mode;
        config false;
        description
          "Indicates the number of online users of a specified CPE mode.";
        ext:support-filter "true";
      }
      leaf interface-name {
        type string {
          length "1..49";
        }
        config false;
        description
          "Specifies the number of online users that get online from a specified interface.";
        ext:support-filter "true";
      }
      leaf vpn-name {
        type string {
          length "1..31";
        }
        config false;
        description
          "Specifies the number of online users of a specified VPN instance.";
        ext:support-filter "true";
      }
      leaf pevlan-start-id {
        type uint16 {
          range "0..4094";
        }
        config false;
        description
          "Displays the start VLANID in the outer VLAN range.";
        ext:support-filter "true";
      }
      leaf pevlan-end-id {
        type uint16 {
          range "0..4094";
        }
        config false;
        description
          "Displays the End VLANID in the outer VLAN range.";
        ext:support-filter "true";
      }
      leaf cevlan-start-id {
        type uint16 {
          range "0..4094";
        }
        config false;
        description
          "Displays the start VLANID in the inner VLAN range.";
        ext:support-filter "true";
      }
      leaf cevlan-end-id {
        type uint16 {
          range "0..4094";
        }
        config false;
        description
          "Displays the End VLANID in the inner VLAN range.";
        ext:support-filter "true";
      }
      leaf slot-id {
        type string {
          length "1..15";
        }
        config false;
        description
          "The slot ID range is determined by the device model.";
        ext:support-filter "true";
      }
      leaf card-id {
        type uint8 {
          range "0..255";
        }
        config false;
        description
          "The subcard ID range is determined by the device model.";
        ext:support-filter "true";
      }
      leaf total-users {
        type uint32;
        config false;
        description
          "Total Users.";
      }
      leaf ipv4-users {
        type uint32;
        config false;
        description
          "IPv4 users.";
      }
      leaf ipv6-users {
        type uint32;
        config false;
        description
          "IPv6 users.";
      }
      leaf dual-users {
        type uint32;
        config false;
        description
          "Dual users.";
      }
    }
    container access-online-number-by-user-types {
      config false;
      description
        "List of vBRAS-UP online users based on a specified user type.";
      list access-online-number-by-user-type {
        key "up-id user-type";
        description
          "Statistics of vBRAS-UP online users based on a specified user type.";
        leaf up-id {
          type uint32 {
            range "1024..2023 | 2048..3047 | 3072..4071 | 4096..5095";
          }
          description
            "ID of a vBRAS-UP.";
        }
        leaf user-type {
          type enumeration {
            enum "ppp"{
              value 0;
              description
                "PPP user.";
            }
            enum "l2tp"{
              value 1;
              description
                "L2TP user.";
            }
            enum "ip"{
              value 2;
              description
                "IP user.";
            }
          }
          description
            "Type of user.";
        }
        uses online-user-number;
      }
    }
    container access-online-number-by-domains {
      config false;
      description
        "List of vBRAS-UP online users based on a specified domain.";
      list access-online-number-by-domain {
        key "up-id domain-name";
        description
          "Statistics of vBRAS-UP online users based on a specified domain.";
        leaf up-id {
          type uint32 {
            range "1024..2023 | 2048..3047 | 3072..4071 | 4096..5095";
          }
          description
            "ID of a vBRAS-UP.";
        }
        leaf domain-name {
          type string {
            length "1..64";
          }
          description
            "Domain name.";
        }
        uses online-user-number;
      }
    }
    container access-online-number-by-filters {
      config false;
      description
        "List of vBRAS-UP online users based on a specified filter.";
      list access-online-number-by-filter {
        key "up-id";
        description
          "Statistics of vBRAS-UP online users based on a specified filter.";
        leaf up-id {
          type uint32 {
            range "1024..2023 | 2048..3047 | 3072..4071 | 4096..5095";
          }
          description
            "ID of a vBRAS-UP.";
        }
        uses online-user-number;
      }
    }
    container access-online-number-upmng-instances {
      config false;
      description
        "List of the number of online users based on UPMNG instances.";
      list access-online-number-upmng-instance {
        key "upmng-instance";
        description
          "Statistics of the number of online users based on UPMNG instances.";
        leaf upmng-instance {
          type string {
            length "1..15";
          }
          description
            "UPMNG instance name.";
        }
        uses online-user-number;
        container independent-ups {
          description
            "List of the number of online users based on independent vBRAS-UPs.";
          list independent-up {
            key "up-id";
            description
              "Statistics of the number of online users based on independent vBRAS-UPs.";
            leaf up-id {
              type uint32 {
                range "1024..2023 | 2048..3047 | 3072..4071 | 4096..5095";
              }
              description
                "ID of a vBRAS-UP.";
            }
            uses online-user-number;
          }
        }
        container up-backup-groups {
          description
            "List of the number of online users based on the vBRAS-UP backup group.";
          list up-backup-group {
            key "group-name";
            description
              "Statistics of the number of online users based on the vBRAS-UP backup group.";
            leaf group-name {
              type string {
                length "1..15";
              }
              description
                "Name of a vBRAS-UP backup group.";
            }
            uses online-user-number;
            container backup-group-up-ids {
              description
                "List of the number of online users in a vBRAS-UP backup group based on the vBRAS-UP ID.";
              list backup-group-up-id {
                key "up-id";
                description
                  "Statistics of the number of online users in a vBRAS-UP backup group based on the vBRAS-UP ID.";
                leaf up-id {
                  type uint32 {
                    range "1024..2023 | 2048..3047 | 3072..4071 | 4096..5095";
                  }
                  description
                    "ID of a vBRAS-UP.";
                }
                uses online-user-number;
              }
            }
          }
        }
      }
    }
    container access-tables {
      config false;
      description
        "List of the user access statistics tables.";
      list access-table {
        key "access-index";
        config false;
        description
          "Statistics of user access statistics table.";
        leaf access-index {
          type uint32;
          config false;
          description
            "Access user index.";
        }
        leaf pevlan-start {
          type int32 {
            range "0..4094";
          }
          config false;
          description
            "PE-VLAN start ID.";
          ext:support-filter "true";
        }
        leaf pevlan-end {
          type int32 {
            range "0..4094";
          }
          config false;
          description
            "PE-VLAN end ID.";
          ext:support-filter "true";
        }
        leaf cevlan-start {
          type int32 {
            range "0..4094";
          }
          config false;
          description
            "CE-VLAN start ID.";
          ext:support-filter "true";
        }
        leaf cevlan-end {
          type int32 {
            range "0..4094";
          }
          config false;
          description
            "CE-VLAN end ID.";
          ext:support-filter "true";
        }
        leaf access-interface {
          type string {
            length "1..63";
          }
          config false;
          description
            "User access interface.";
          ext:support-filter "true";
        }
        leaf access-slot-number {
          type int32 {
            range "0..509600";
          }
          config false;
          description
            "Slot Number.";
          ext:support-filter "true";
        }
        leaf access-slot {
           type string {
            length "1..32";
          }
          description
            "This node applies to scenarios where the vBRAS-UP or device has been enabled with virtual access. In this case, the slot ID is in the 1024/1 or clc1/2 format.";
        }
        container access-user-basic-info {
          config false;
          description
            "Statistics of the access user basic info.";
          leaf access-user-name {
            type string {
              length "1..253";
            }
            config false;
            description
              "Access user name.";
            ext:support-filter "true";
          }
          leaf access-port-type {
            type bras-user-manage-port-type;
            config false;
            description
              "Access port type.";
          }
          leaf access-sub-slot-number {
            type int32 {
              range "0..2147483647";
            }
            config false;
            description
              "Subslot Number.";
          }
          leaf access-port-number {
            type int32 {
              range "0..2147483647";
            }
            config false;
            description
              "Port Number.";
          }
          leaf access-vlan-id {
            type int32 {
              range "0..2147483647";
            }
            config false;
            description
              "VLAN id.";
          }
          leaf access-authen-method {
            type bras-user-manage-authen-method;
            config false;
            description
              "Authentication method.";
          }
          leaf access-account-method {
            type bras-user-manage-account-method;
            config false;
            description
              "Account method.";
          }
          leaf access-ipaddress {
            type inet:ipv4-address-no-zone;
            config false;
            description
              "IP address.";
          }
          leaf access-mac-address {
            type pub-type:mac-address {
              length "0..255";
            }
            config false;
            description
              "Mac address.";
          }
          leaf access-start-time {
            type string {
              length "1..23";
            }
            config false;
            description
              "Start time.";
          }
          leaf access-basic-ip-type {
            type string {
              length "1..49";
            }
            config false;
            description
              "The basic service type. UCHAR[0]-IPv4, UCHAR[1]-IPv6, UCHAR[2]-IPv6-PD. '0'-without such basic service, '1'-with such basic service.";
          }
          leaf access-ipv6-wait-delay {
            type int32 {
              range "30..120";
            }
            config false;
            description
              "The time of waiting for DHCPv6 packet after IPv6CP negotiation.";
          }
          leaf ipv6-managed-address-method {
            type bras-user-manage-ipv6-addr-method;
            config false;
            description
              "The address configuration method for PPP and L2TP user.";
          }
          leaf access-ipv6-cp-with-interface-id {
            type bras-user-manage-truth-value;
            config false;
            description
              "The flag indicating whether PPP and L2TP user will use the interface-id of IPv6cp negotiation in DHCPv6 address allocation.";
          }
          leaf access-ipv6-config-method {
            type bras-user-manage-ipv6-config-method;
            config false;
            description
              "The method PPPoE, L2TP and IPoE users get configuration parameters.";
          }
          leaf access-ipv6-cp-assign-interface-id {
            type bras-user-manage-truth-value;
            config false;
            description
              "The flag indicating whether to accept user's interface-id when IPv6 CP negotiation.";
          }
          leaf rui-type {
            type bras-user-manage-rui-type-value;
            config false;
            description
              "RUI type.";
          }
          leaf access-type {
            type string {
              length "1..64";
            }
            config false;
            description
              "The user access type.";
          }
          leaf access-phy-interface {
            type string {
              length "1..63";
            }
            config false;
            description
              "User access physical interface.";
          }
          leaf access-authen-ip-type {
            type string {
              length "1..3";
            }
            config false;
            description
              "The authen service type. UCHAR[0]-IPv4, UCHAR[1]-IPv6, UCHAR[2]-IPv6-PD. '0'-without such authen service, '1'-with such authen service.";
          }
          leaf used-flag {
            type bras-user-manage-common-enable-type;
            config false;
            description
              "State of a user.";
          }
          leaf used-type {
            type bras-user-manage-used-type;
            config false;
            description
              "User active type.";
          }
          leaf username-rd {
            type bras-user-manage-common-enable-type;
            config false;
            description
              "User name delivered by the RADIUS server.";
          }
          leaf domain-name {
            type string {
              length "1..64";
            }
            config false;
            description
              "Name of a domain.";
          }
          leaf domain-map-name {
            type string {
              length "1..64";
            }
            config false;
            description
              "MAP domain name.";
          }
          leaf domainname-rd {
            type bras-user-manage-common-enable-type;
            config false;
            description
              "Domain name delivered by the RADIUS server.";
          }
          leaf backup-state {
            type bras-user-manage-backup-state;
            config false;
            description
              "User backup state.";
          }
          leaf ipv6-backup-state {
            type bras-user-manage-backup-state;
            config false;
            description
              "User backup state.";
          }
          leaf rbp-state {
            type bras-user-manage-rbp-state;
            config false;
            description
              "User master/backup state.";
          }
          leaf callnum {
            type string {
              length "1..256";
            }
            config false;
            description
              "Calling number.";
          }
          leaf out-bound-slot {
            type uint8 {
              range "0..255";
            }
            config false;
            description
              "Physical interface for user access.";
          }
          leaf port-limit {
            type uint32 {
              range "0..4294967295";
            }
            config false;
            description
              "Maximum number of users.";
          }
          leaf port-limit-rd {
            type bras-user-manage-common-enable-type;
            config false;
            description
              "Domain name delivered by the RADIUS server.";
          }
          leaf vpnname {
            type string {
              length "1..32";
            }
            config false;
            description
              "Name of a VPN instance.";
          }
          leaf vpnname-rd {
            type bras-user-manage-common-enable-type;
            config false;
            description
              "VPN name delivered by the RADIUS server.";
          }
          leaf inbound-vpnname {
            type string {
              length "1..32";
            }
            config false;
            description
              "Upstream VPN instance name.";
          }
          leaf inboundvpnname-rd {
            type bras-user-manage-common-enable-type;
            config false;
            description
              "Upstream VPN name delivered by the RADIUS server.";
          }
          leaf ipv6-vpnname {
            type string {
              length "1..32";
            }
            config false;
            description
              "IPv6 VPN instance name.";
          }
          leaf ipv6vpnname-rd {
            type bras-user-manage-common-enable-type;
            config false;
            description
              "IPv6 VPN name delivered by the RADIUS server.";
          }
          leaf ipv6inbound-vpnname {
            type string {
              length "1..32";
            }
            config false;
            description
              "IPv6 upstream VPN instance name.";
          }
          leaf ipv6inboundvpnname-rd {
            type bras-user-manage-common-enable-type;
            config false;
            description
              "IPv6 upstream VPN name delivered by the RADIUS server.";
          }
          leaf usr-ipaddr-mask {
            type inet:ipv4-address-no-zone;
            config false;
            description
              "IP subnet mask of a user.";
          }
          leaf usr-ipaddr-mask-rd {
            type bras-user-manage-common-enable-type;
            config false;
            description
              "IP subnet mask delivered by the RADIUS server.";
          }
          leaf gate-way-addr {
            type inet:ipv4-address-no-zone;
            config false;
            description
              "Gateway address of a user.";
          }
          leaf gate-way-addr-rd {
            type bras-user-manage-common-enable-type;
            config false;
            description
              "The RADIUS server delivers the NMS address.";
          }
          leaf framed-route {
            type inet:ipv4-address-no-zone;
            config false;
            description
              "IP address in the Framed-Route attribute delivered to a user.";
          }
          leaf framed-route-mask-len {
            type uint8 {
              range "0..255";
            }
            config false;
            description
              "Mask length in the Framed-Route attribute delivered to a user.";
          }
          leaf next-ip {
            type inet:ipv4-address-no-zone;
            config false;
            description
              "Next-hop address in the Framed-Route attribute delivered to a user.";
          }
          leaf meric {
            type uint32 {
              range "0..4294967295";
            }
            config false;
            description
              "Metric in the Framed-Route attribute delivered to a user.";
          }
          leaf frame-route-rd {
            type bras-user-manage-common-enable-type;
            config false;
            description
              "Framed-Route delivered by the RADIUS server.";
          }
          leaf frame-route-num {
            type uint32 {
              range "0..4294967295";
            }
            config false;
            description
              "Number of Framed-Route attributes delivered to a user.";
          }
          leaf ipv6lla-addr-pre {
            type inet:ipv6-address-no-zone;
            config false;
            description
              "NDRA prefix of a user.";
          }
          leaf ipv6-addr-pre-rd {
            type bras-user-manage-common-enable-type;
            config false;
            description
              "User NDRA prefix delivered by the RADIUS server.";
          }
          leaf ipv6-addr {
            type inet:ipv6-address-no-zone;
            config false;
            description
              "IPv6 address of a user.";
          }
          leaf ipv6-addr-rd {
            type bras-user-manage-common-enable-type;
            config false;
            description
              "IPv6 address of the user delivered by the RADIUS server.";
          }
          leaf ipv6-pd-addr-pre {
            type inet:ipv6-address-no-zone;
            config false;
            description
              "PD prefix of a user.";
          }
          leaf ipv6-pd-addr-pre-rd {
            type bras-user-manage-common-enable-type;
            config false;
            description
              "PD prefix delivered by the RADIUS server.";
          }
          leaf frame-v6-route-ipaddr {
            type inet:ipv6-address-no-zone;
            config false;
            description
              "IP address in the Framed-IPv6-Route attribute delivered to a user.";
          }
          leaf frame-v6-route-ipaddr-prefix-len {
            type uint32 {
              range "0..4294967295";
            }
            config false;
            description
              "Prefix length of IP address in the Framed-IPv6-Route attribute delivered to a user.";
          }
          leaf frame-v6-route-rd {
            type bras-user-manage-common-enable-type;
            config false;
            description
              "Framed-IPv6-Route prefix delivered by the RADIUS server to a user.";
          }
          leaf frame-v6-route-num {
            type uint32 {
              range "0..4294967295";
            }
            config false;
            description
              "Number of Framed-IPv6-Route attributes delivered to a user.";
          }
          leaf dhcpserver-ip {
            type inet:ipv4-address-no-zone;
            config false;
            description
              "IP address of a DHCP server.";
          }
          leaf v6-addr-assign-mode {
            type bras-user-manage-v6ad-assign-mode-type;
            config false;
            description
              "Mode for allocating IPv6 addresses.";
          }
          leaf ralink-prefix {
            type bras-user-manage-common-enable-type;
            config false;
            description
              "Whether a device is enabled to send RA packets carrying the first 64 bits of the addresses assigned to IPv6 users as on-link prefixes.";
          }
          leaf ipv6-cp-receive-user-interface-id {
            type uint8 {
              range "0..255";
            }
            config false;
            description
              "ID of the interface for IPCPv6 negotiation of a PPPv6 user.";
          }
          leaf hex-lineid {
            type string {
              length "1..200";
            }
            config false;
            description
              "Access-Line-Id information.";
          }
          leaf char-lineid {
            type string {
              length "1..200";
            }
            config false;
            description
              "Access-Line-Id information.";
          }
          leaf lineid-type {
            type bras-user-manage-line-id-type;
            config false;
            description
              "Access-Line-Id type.";
          }
          leaf agent-circuit-id {
            type string {
              length "1..200";
            }
            config false;
            description
              "Agent-Circuit-Id information.";
            ext:support-filter "true";
          }
          leaf agent-remote-id {
            type string {
              length "1..200";
            }
            config false;
            description
              "Agent-Remote-Id information.";
          }
          leaf option37info {
            type string {
              length "1..127";
            }
            config false;
            description
              "DHCPv6 Option 37 information.";
          }
          leaf option38info {
            type string {
              length "1..127";
            }
            config false;
            description
              "DHCPv6 Option 38 information.";
          }
          leaf ip4-leas-coa0-flg {
            type bras-user-manage-common-enable-type;
            config false;
            description
              "Whether the lease delivered in a CoA message is zero.";
          }
          leaf ip4-start-leas {
            type string {
              length "1..31";
            }
            config false;
            description
              "IPv4 start lease of a user.";
          }
          leaf ip4-end-leas {
            type string {
              length "1..31";
            }
            config false;
            description
              "IPv4 end lease of a user.";
          }
          leaf ip4-leas-rds-flg {
            type bras-user-manage-common-enable-type;
            config false;
            description
              "IPv4 continuous lease.";
          }
          leaf ip4-ori-leas {
            type uint32 {
              range "0..4294967295";
            }
            units s;
            config false;
            description
              "IPv4 original lease.";
          }
          leaf ip4-rem-leas {
            type uint32 {
              range "0..4294967295";
            }
            units s;
            config false;
            description
              "IPv4 remaining lease of a user.";
          }
          leaf ip4-rem-leas-rds {
            type bras-user-manage-common-enable-type;
            config false;
            description
              "Indicates the remaining lease of the user IPv4 delivered by the RADIUS server.";
          }
          leaf ip6-start-leas {
            type string {
              length "1..31";
            }
            config false;
            description
              "IPv6 start lease of a user.";
          }
          leaf ip6-end-leas {
            type string {
              length "1..31";
            }
            config false;
            description
              "IPv6 end lease of a user.";
          }
          leaf ip6-leas-rds-flg {
            type bras-user-manage-common-enable-type;
            config false;
            description
              "Indicates the lease of the user IPv6 delivered by the RADIUS server.";
          }
          leaf ip6-leas-end-tim {
            type uint32 {
              range "0..4294967295";
            }
            units s;
            config false;
            description
              "IPv6 continuous lease.";
          }
          leaf ip6-rem-leas {
            type uint32 {
              range "0..4294967295";
            }
            units s;
            config false;
            description
              "IPv6 remaining lease of a user.";
          }
          leaf ip6-rem-leas-rds {
            type bras-user-manage-common-enable-type;
            config false;
            description
              "Indicates the remaining lease of the user IPv6 delivered by the RADIUS server.";
          }
          leaf usr-grp-name {
            type string {
              length "1..32";
            }
            config false;
            description
              "Name of a user group.";
          }
          leaf usr-grp-rds-flg {
            type bras-user-manage-common-enable-type;
            config false;
            description
              "RADIUS server delivers the user group.";
          }
          leaf nxt-hop {
            type inet:ipv4-address-no-zone;
            config false;
            description
              "Next-hop IP address.";
          }
          leaf nxt-hop-rds-flg {
            type bras-user-manage-common-enable-type;
            config false;
            description
              "RADIUS server delivers the next hop address of the user.";
          }
          leaf ip6-plcy-addr {
            type inet:ipv6-address-no-zone;
            config false;
            description
              "Next-hop IPv6 address.";
          }
          leaf ip6-plcy-addr-rds {
            type bras-user-manage-common-enable-type;
            config false;
            description
              "RADIUS server delivers the IPv6 next hop address of the user.";
          }
          leaf map-ipv4-addr {
            type inet:ipv4-address-no-zone;
            config false;
            description
              "MAP IPv4 address.";
          }
          leaf map-ipv4-prefix-addr {
            type inet:ipv4-address-no-zone;
            config false;
            description
              "MAP IPv4 prefix.";
          }
          leaf map-ipv4-prefix-len {
            type uint8 {
              range "0..255";
            }
            config false;
            description
              "Length of an MAP IPv4 prefix.";
          }
          leaf map-psid {
            type uint16;
            config false;
            description
              "MAP PSID value.";
          }
          leaf map-psid-offet {
            type uint8 {
              range "0..255";
            }
            config false;
            description
              "PSID offset value.";
          }
          leaf nat-ipaddr {
            type inet:ipv4-address-no-zone;
            config false;
            description
              "NAT IP address.";
          }
          leaf nat-start-port {
            type uint16;
            config false;
            description
              "NAT start port.";
          }
          leaf nat-end-port {
            type uint16;
            config false;
            description
              "NAT end port.";
          }
          leaf nat-port-rds-flg {
            type bras-user-manage-common-enable-type;
            description
              "NAT port range of the user delivered by the RADIUS server.";
          }
        }
        container access-user-aaa-info {
          config false;
          description
            "Statistics of user access AAA information.";
          leaf access-if-idle-cut {
            type bras-user-manage-truth-value;
            config false;
            description
              "Indicates whether to use idle-cut.";
          }
          leaf access-idle-cut-time {
            type uint32 {
              range "0..4294967295";
            }
            config false;
            description
              "Idle cut time.";
          }
          leaf access-idle-cut-flow {
            type int32 {
              range "0..2147483647";
            }
            config false;
            description
              "Idle cut flow.";
          }
          leaf dns-addr {
            type inet:ipv4-address-no-zone;
            config false;
            description
              "Primary DNS server.";
          }
          leaf dns-addr-rd {
            type bras-user-manage-common-enable-type;
            config false;
            description
              "RADIUS server delivers the master DNS server.";
          }
          leaf dns-sec-addr {
            type inet:ipv4-address-no-zone;
            config false;
            description
              "Secondary DNS server.";
          }
          leaf dns-sec-addr-rd {
            type bras-user-manage-common-enable-type;
            config false;
            description
              "RADIUS server delivers the second DNS server.";
          }
          leaf usr-ipaddr-rd {
            type bras-user-manage-common-enable-type;
            config false;
            description
              "RADIUS server delivers the user IP address.";
          }
          leaf ifid {
            type string {
              length "1..256";
            }
            config false;
            description
              "IPv6 interface ID of a user.";
          }
          leaf ifid-rd {
            type bras-user-manage-common-enable-type;
            config false;
            description
              "IPv6 interface ID delivered by the RADIUS server.";
          }
          leaf lla-addr {
            type inet:ipv6-address-no-zone;
            config false;
            description
              "IPv6 link-local address of a user.";
          }
          leaf v6duiid {
            type string {
              length "1..255";
            }
            config false;
            description
              "DUID of an IPv6 user.";
          }
          leaf dns-pri-v6-ip {
            type inet:ipv6-address-no-zone;
            config false;
            description
              "Primary DNSv6 server address of a user.";
          }
          leaf dns-pri-v6-ip-rd {
            type bras-user-manage-common-enable-type;
            config false;
            description
              "RADIUS server delivers the user IPv6 master DNS server.";
          }
          leaf dns2st-pri-v6-ip {
            type inet:ipv6-address-no-zone;
            config false;
            description
              "Secondary DNSv6 server address of a user.";
          }
          leaf dns2st-v6-ip-rd {
            type bras-user-manage-common-enable-type;
            config false;
            description
              "RADIUS server delivers the user IPv6 second DNS server.";
          }
          leaf dns3st-pri-v6-ip {
            type inet:ipv6-address-no-zone;
            config false;
            description
              "Third DNSv6 server address of a user.";
          }
          leaf dns3st-pri-v6-ip-rd {
            type bras-user-manage-common-enable-type;
            config false;
            description
              "RADIUS server delivers the user IPv6 the third DNS server.";
          }
          leaf dns4st-pri-v6-ip {
            type inet:ipv6-address-no-zone;
            config false;
            description
              "Fourth DNSv6 server address of a user.";
          }
          leaf dns4st-pri-v6-ip-rd {
            type bras-user-manage-common-enable-type;
            config false;
            description
              "RADIUS server delivers the user IPv6 the fourth DNS server.";
          }
          leaf cpe-ipv4 {
            type bras-user-manage-common-enable-type;
            config false;
            description
              "User IPv4 authorization type enable.";
          }
          leaf cpe-ipv6 {
            type bras-user-manage-common-enable-type;
            config false;
            description
              "User IPv6 authorization type enable.";
          }
          leaf cpe-ipv6-pd {
            type bras-user-manage-common-enable-type;
            config false;
            description
              "User IPv6-PD authorization type enable.";
          }
          leaf basic-service-ipv4 {
            type bras-user-manage-common-enable-type;
            config false;
            description
              "User IPv4 basic type enable.";
          }
          leaf basic-service-ipv6 {
            type bras-user-manage-common-enable-type;
            config false;
            description
              "User IPv6 basic type enable.";
          }
          leaf basic-service-ipv6-pd {
            type bras-user-manage-common-enable-type;
            config false;
            description
              "User IPv6-PD basic type enable.";
          }
          leaf mirror-policy-name {
            type string {
              length "1..64";
            }
            config false;
            description
              "Name of a mirroring policy.";
          }
          leaf rds-template-name {
            type string {
              length "1..34";
            }
            config false;
            description
              "RADIUS server template.";
          }
          leaf tac-tmp-group-name {
            type string {
              length "1..32";
            }
            config false;
            description
              "HWTACACS server template.";
          }
          leaf sec-st-rds-template-name {
            type string {
              length "1..34";
            }
            config false;
            description
              "Server template for second accounting.";
          }
          leaf phy-rds-template-name {
            type string {
              length "1..34";
            }
            config false;
            description
              "Server template for physical accounting.";
          }
          leaf edsg-rds-template-name {
            type string {
              length "1..34";
            }
            config false;
            description
              "Accounting copy server (EDSG).";
          }
          leaf tmp-rds-template-name {
            type string {
              length "1..34";
            }
            config false;
            description
              "RADIUS server template for LLID authentication.";
          }
          leaf cur-authen-result {
            type bras-user-manage-result-type;
            config false;
            description
              "Current authentication mode.";
          }
          leaf authored-place {
            type bras-user-manage-author-method;
            config false;
            description
              "Current authorization mode.";
          }
          leaf authored-result {
            type bras-user-manage-author-result-type;
            config false;
            description
              "Authorization result.";
          }
          leaf action-flag {
            type bras-user-manage-access-action-flag;
            config false;
            description
              "Action flag.";
          }
          leaf authen-state {
            type bras-user-manage-user-authenstate;
            config false;
            description
              "Authentication state.";
          }
          leaf author-state {
            type bras-user-manage-user-author-state;
            config false;
            description
              "Authorization state.";
          }
          leaf acct-method {
            type bras-user-manage-account-method;
            config false;
            description
              "Configured accounting method.";
          }
          leaf quota-outaction {
            type bras-user-manage-quota-action-type;
            config false;
            description
              "Action taken upon quota exhaustion.";
          }
          leaf current-acct-method {
            type bras-user-manage-account-method;
            config false;
            description
              "Current accounting method.";
          }
          leaf direct-url {
            type string {
              length "1..200";
            }
            config false;
            description
              "UCL for redirecting users upon quota exhaustion.";
          }
          leaf lease-timeout-offline-flag {
            type bras-user-manage-common-enable-type;
            config false;
            description
              "User is in arrears.";
          }
          leaf rtacct-interval {
            type uint32 {
              range "0..4294967295";
            }
            config false;
            description
              "Real-time accounting interval.";
          }
          leaf rtacct-flg {
            type bras-user-manage-common-enable-type;
            config false;
            description
              "Real-time accounting is enabled.";
          }
          leaf rtacct-interval-rd {
            type bras-user-manage-common-enable-type;
            config false;
            description
              "RADIUS server delivers the real-time accounting function to the user.";
          }
          leaf rtacct-send {
            type bras-user-manage-common-enable-type;
            config false;
            description
              "Sending update packets in real time.";
          }
          leaf rttraffic-update {
            type bras-user-manage-common-enable-type;
            config false;
            description
              "Real-time accounting packets are sent during traffic update.";
          }
          leaf acc-starttime {
            type string {
              length "1..31";
            }
            config false;
            description
              "Time when accounting starts.";
          }
          leaf acc-onlinetime {
            type string {
              length "1..31";
            }
            config false;
            description
              "Online duration of a user.";
          }
          leaf acct-state {
            type bras-user-manage-user-acct-state;
            config false;
            description
              "Accounting state.";
          }
          leaf acct-session-id {
            type string {
            length "1..49";
            }
            config false;
            description
              "Accounting session ID.";
          }
          leaf tim-limt {
            type uint32 {
              range "0..4294967295";
            }
            units s;
            config false;
            description
              "Remaining period.";
          }
          leaf tim-limt-rds-flg {
            type bras-user-manage-common-enable-type;
            config false;
            description
              "Remaining time of the user delivered by the RADIUS server.";
          }
          leaf tim-remain {
            type uint32 {
              range "0..4294967295";
            }
            units s;
            config false;
            description
              "Remaining time.";
          }
          leaf flw-limt-high {
            type uint32 {
              range "0..4294967295";
            }
            units Byte;
            config false;
            description
              "Remaining traffic (high).";
          }
          leaf flw-limt-low {
            type uint32 {
              range "0..4294967295";
            }
            units Byte;
            config false;
            description
              "Remaining traffic (low).";
          }
          leaf flw-limt-rds-flg {
            type bras-user-manage-common-enable-type;
            config false;
            description
              "The RADIUS server delivers the remaining traffic of the user.";
          }
          leaf idle-cut-dir {
            type bras-user-manage-direction-type;
            config false;
            description
              "Idle-cut direction.";
          }
          leaf idle-cut-rds-flg {
            type bras-user-manage-common-enable-type;
            config false;
            description
              "The RADIUS server delivers the user idle-cut information.";
          }
          leaf ip4-acct-flw {
            type uint32 {
              range "0..4294967295";
            }
            config false;
            description
              "IPv4 real-time total rate.";
          }
          leaf ip4-acct-byt-flg {
            type bras-user-manage-byte-type;
            config false;
            description
              "IPv4 real-time total rate unit.";
          }
          leaf ip4-acct-up-flw {
            type uint32 {
              range "0..4294967295";
            }
            config false;
            description
              "Upstream rate for sending IPv4 real-time accounting packets.";
          }
          leaf ip4-acct-up-byt-flg {
            type bras-user-manage-byte-type;
            config false;
            description
              "IPv4 upstream real-time rate unit.";
          }
          leaf ip4-acct-dn-flw {
            type uint32 {
              range "0..4294967295";
            }
            config false;
            description
              "IPv4 downstream real-time rate.";
          }
          leaf ip4-acct-dn-byt-flg {
            type bras-user-manage-byte-type;
            config false;
            description
              "IPv4 downstream real-time rate unit.";
          }
          leaf ip6-acct-flw {
            type uint32 {
              range "0..4294967295";
            }
            config false;
            description
              "IPv6 real-time total rate.";
          }
          leaf ip6-acct-byt-flg {
            type bras-user-manage-byte-type;
            config false;
            description
              "IPv6 real-time total rate unit.";
          }
          leaf ip6-acct-up-flw {
            type uint32 {
              range "0..4294967295";
            }
            config false;
            description
              "IPv6 Upstream real-time rate.";
          }
          leaf ip6-acct-up-byt-flg {
            type bras-user-manage-byte-type;
            config false;
            description
              "IPv6 Upstream real-time rate unit.";
          }
          leaf ip6-acct-dn-flw {
            type uint32 {
              range "0..4294967295";
            }
            config false;
            description
              "IPv6 downstream real-time rate.";
          }
          leaf ip6-acct-dn-byt-flg {
            type bras-user-manage-byte-type;
            config false;
            description
              "IPv6 downstream real-time rate unit.";
          }
          leaf acct-delay-flg {
            type bras-user-manage-common-enable-type;
            config false;
            description
              "Accounting delay flag.";
          }
          leaf acct-delay-tim {
            type uint16;
            units s;
            config false;
            description
              "Accounting delay time.";
          }
          leaf acct-delay-pas-tim {
            type uint32 {
              range "0..4294967295";
            }
            units s;
            config false;
            description
              "Time elapsed after the delay time expires.";
          }
          leaf acct-delay-act {
            type bras-user-manage-online-type;
            config false;
            description
              "Action taken after the delay time expires.";
          }
          leaf usr-pri {
            type uint8 {
              range "0..255";
            }
            config false;
            description
              "Priority of a user.";
          }
          leaf web-url {
            type string {
              length "1..201";
            }
            config false;
            description
              "Redirection web URL.";
          }
          leaf web-url-rds-flg {
            type bras-user-manage-common-enable-type;
            config false;
            description
              "The RADIUS server delivers the user redirection URL.";
          }
          leaf class-opt61 {
            type string {
              length "1..255";
            }
            config false;
            description
              "No. 25 attribute Serial-Number.";
          }
          leaf auto-adapt-flg {
            type bras-user-manage-common-enable-type;
            config false;
            description
              "Automatic link bandwidth adjustment.";
          }
          leaf up-priority {
            type bras-user-manage-priority-type;
            config false;
            description
              "Upstream priority of a user.";
          }
          leaf up-priority-rd {
            type bras-user-manage-common-enable-type;
            config false;
            description
              "RADIUS server delivers the user upstream priority.";
          }
          leaf down-priority {
            type bras-user-manage-priority-type;
            config false;
            description
              "Downstream priority of a user.";
          }
          leaf down-priority-rd {
            type bras-user-manage-common-enable-type;
            config false;
            description
              "RADIUS server delivers the user downstream priority.";
          }
          leaf author-ds-name {
            type string {
              length "1..51";
            }
            config false;
            description
              "Diffserv domain for authorization.";
          }
          leaf real-ds-name {
            type string {
              length "1..51";
            }
            config false;
            description
              "Diffserv domain that takes effect.";
          }
          leaf pcp-flg {
            type bras-user-manage-common-enable-type;
            config false;
            description
              "PCP enable.";
          }
          leaf pcp-rds-flg {
            type bras-user-manage-common-enable-type;
            config false;
            description
              "Enable the RADIUS server to deliver user PCP.";
          }
          leaf ipv4-mtu {
            type uint16;
            units Byte;
            config false;
            description
              "Maximum transmission unit.";
          }
          leaf ipv4-mtu-rds-flg {
            type bras-user-manage-common-enable-type;
            config false;
            description
              "RADIUS server delivers the user MTU.";
          }
          leaf ipv6-mtu {
            type uint16;
            units Byte;
            config false;
            description
              "IPv6 maximum transmission unit.";
          }
          leaf ipv6-mtu-rds-flg {
            type bras-user-manage-common-enable-type;
            config false;
            description
              "RADIUS server delivers the user IPv6 MTU.";
          }
          leaf mru {
            type uint16;
            units Byte;
            config false;
            description
              "Maximum receive unit.";
          }
          leaf clng-sta-id {
            type string {
              length "1..253";
            }
            config false;
            description
              "Calling-Station-Id attribute.";
          }
          leaf clng-sta-id-rds-flg {
            type bras-user-manage-common-enable-type;
            config false;
            description
              "RADIUS server delivers the user Calling-station-id.";
          }
          leaf access-real-idle-cut-time {
            type uint32 {
              range "0..4294967295";
            }
            units s;
            config false;
            description
              "Real idle cut time.";
          }        
          container access-user-class-infos {
            config false;
            description
              "List of the user class.";
            list access-user-class-info {
              key "class-num";
              config false;
              description
                "Statistics of the user class.";
              leaf class-num {
                type uint8 {
                  range "0..255";
                }
                config false;
                description
                  "Class information index.";
              }
              leaf classinfo {
                type string {
                  length "1..200";
                }
                config false;
                description
                  "Information about the No.25 Class attribute.";
              }
              leaf hexclassinfo {
                type string {
                  length "1..200";
                }
                config false;
                description
                  "Information about the No.25 Class attribute (hexadecimal).";
              }
              leaf classinfo-rd {
                type bras-user-manage-common-enable-type;
                config false;
                description
                  "No.25 attribute is delivered by the RADIUS server.";
              }
            }
          }
        }
        container access-user-dot1x-mcast-info {
          config false;
          description
            "Statistics of the access user dot1x mcast.";
          leaf msi-dsn-name {
            type string {
              length "1..16";
            }
            config false;
            description
              "User identifier information in the MSISDN field.";
          }
          leaf msi-dsn-name-rd {
            type bras-user-manage-common-enable-type;
            config false;
            description
              "MSISDN is delivered by the RADIUS server.";
          }
          leaf eapuser-flg {
            type bras-user-manage-common-enable-type;
            config false;
            description
              "EAP user.";
          }
          leaf md5-end-flg {
            type bras-user-manage-common-enable-type;
            config false;
            description
              "MD5 termination.";
          }
          leaf iptv-prof {
            type string {
              length "1..32";
            }
            config false;
            description
              "Program profile.";
          }
          leaf iptv-prof-rds-flg {
            type bras-user-manage-common-enable-type;
            config false;
            description
              "User program profile delivered by the RADIUS server.";
          }
          leaf ip6tv-prof {
            type string {
              length "1..32";
            }
            config false;
            description
              "IPv6 program profile.";
          }
          leaf ip6tv-prof-rds-flg {
            type bras-user-manage-common-enable-type;
            config false;
            description
              "IPv6 program profile delivered by the RADIUS server.";
          }
          leaf max-lst-num {
            type uint32 {
              range "0..4294967295";
            }
            config false;
            description
              "Maximum number of multicast programs.";
          }
          leaf max-lst-num-rds-flg {
            type bras-user-manage-common-enable-type;
            config false;
            description
              "Maximum number of multicast programs delivered by the RADIUS server.";
          }
          leaf igmp-en {
            type bras-user-manage-common-enable-type;
            config false;
            description
              "IGMP enable.";
          }
          leaf igmp-en-rds-flg {
            type bras-user-manage-common-enable-type;
            config false;
            description
              "IGMP enable delivered by the RADIUS server.";
          }
          leaf pim-v4-en {
            type bras-user-manage-common-enable-type;
            config false;
            description
              "PIM-S enable.";
          }
          leaf pim-v6-en {
            type bras-user-manage-common-enable-type;
            config false;
            description
              "PIM-SMv6 enable.";
          }          
        }
        container access-user-acl-qos-info {
          config false;
          description
            "Statistics of the access user acl qos.";
          leaf l2-priority {
            type bras-user-manage-priority-type;
            config false;
            description
              "Layer 2 upstream priority of a user.";
          }
          leaf inbound-gq-name {
            type string {
              length "1..31";
            }
            config false;
            description
              "Upstream user group queue profile.";
          }
          leaf inbound-gq-name-rd {
            type bras-user-manage-common-enable-type;
            config false;
            description
              "Upstream user group queue profile delivered by the RADIUS server.";
          }
          leaf outbound-gq-name {
            type string {
              length "1..31";
            }
            config false;
            description
              "Downstream user group queue profile.";
          }
          leaf outbound-gq-name-rd {
            type bras-user-manage-common-enable-type;
            config false;
            description
              "Downstream user group queue profile delivered by the RADIUS server.";
          }
          leaf online-policy {
            type string {
              length "1..31";
            }
            config false;
            description
              "User data flow policy.";
          }
          leaf online-policy-rd {
            type bras-user-manage-common-enable-type;
            config false;
            description
              "User data flow policy delivered by the RADIUS server.";
          }
          container user-qos-inbound-info {
            config false;
            description
              "Statistics of the user inbound qos.";
            uses bras-user-manage:access-table-qos-info;
          }
          container user-qos-outbound-info {
            config false;
            description
              "Statistics of the user outbound qos.";
            uses bras-user-manage:access-table-qos-info;
          }
          container user-sq-car-insufficient-infos {
            config false;
            description
              "List of boards on which SQ or CAR resources are insufficient for family users.";
            list user-sq-car-insufficient-info {
              key "failslotindex";
              config false;
              description
                "Statistics of a board on which SQ or CAR resources are insufficient for family users.";
              leaf failslotindex {
                type uint32 {
                  range "0..4294967295";
                }
                config false;
                description
                  "Index of a board.";
              }
              leaf failslot-upid {
                type uint32 {
                  range "0..4294967295";
                }
                config false;
                description
                  "ID of the UP on which a board resides.";
              }
              leaf in-family-car-res-fail-slot {
                type bras-user-manage-common-enable-type;
                config false;
                description
                  "Whether upstream user queue resources are insufficient.";
              }
              leaf out-family-car-res-fail-slot {
                type bras-user-manage-common-enable-type;
                config false;
                description
                  "Whether downstream user queue resources are insufficient.";
              }
              leaf in-family-sq-res-fail-slot {
                type bras-user-manage-common-enable-type;
                config false;
                description
                  "Whether upstream family CAR resources are insufficient.";
              }
              leaf out-family-sq-res-fail-slot {
                type bras-user-manage-common-enable-type;
                config false;
                description
                  "Whether downstream family CAR resources are insufficient.";
              }              
            }
          }
          container access-user-effective-slot-infos {
            config false;
            description
              "List of the user queue or CAR information.";
            list access-user-effective-slot-info {
              key "effective-slot-index";
              config false;
              description
                "Statistics of the user queue or CAR information.";
              leaf effective-slot-index {
                type uint32 {
                  range "0..4294967295";
                }
                config false;
                description
                  "Index of a rate information entry.";
              }
              leaf user-queueincir {
                type uint32 {
                  range "0..4294967295";
                }
                units kbit/s;
                config false;
                description
                  "Upstream committed information rate (CIR) of a user queue.";
              }
              leaf user-queueinpir {
                type uint32 {
                  range "0..4294967295";
                }
                units kbit/s;
                config false;
                description
                  "Upstream peak information rate (PIR) of a user queue.";
              }
              leaf user-queueincir1 {
                type uint32 {
                  range "0..4294967295";
                }
                units kbit/s;
                config false;
                description
                  "User queue upstream CIR 1.";
              }
              leaf user-queueinpir1 {
                type uint32 {
                  range "0..4294967295";
                }
                units kbit/s;
                config false;
                description
                  "User queue upstream PIR 1.";
              }
              leaf user-queueincir2 {
                type uint32 {
                  range "0..4294967295";
                }
                units kbit/s;
                config false;
                description
                  "User queue upstream CIR 2.";
              }
              leaf user-queueinpir2 {
                type uint32 {
                  range "0..4294967295";
                }
                units kbit/s;
                config false;
                description
                  "User queue upstream PIR 2.";
              }
              leaf user-queueincir3 {
                type uint32 {
                  range "0..4294967295";
                }
                units kbit/s;
                config false;
                description
                  "User queue upstream CIR 3.";
              }
              leaf user-queueinpir3 {
                type uint32 {
                  range "0..4294967295";
                }
                units kbit/s;
                config false;
                description
                  "User queue upstream PIR 3.";
              }
              leaf user-queueincir4 {
                type uint32 {
                  range "0..4294967295";
                }
                units kbit/s;
                config false;
                description
                  "User queue upstream CIR 4.";
              }
              leaf user-queueinpir4 {
                type uint32 {
                  range "0..4294967295";
                }
                units kbit/s;
                config false;
                description
                  "User queue upstream PIR 4.";
              }
              leaf user-queueincir5 {
                type uint32 {
                  range "0..4294967295";
                }
                units kbit/s;
                config false;
                description
                  "User queue upstream CIR 5.";
              }
              leaf user-queueinpir5 {
                type uint32 {
                  range "0..4294967295";
                }
                units kbit/s;
                config false;
                description
                  "User queue upstream PIR 5.";
              }
              leaf user-queueoutcir {
                type uint32 {
                  range "0..4294967295";
                }
                units kbit/s;
                config false;
                description
                  "Downstream CIR of a user queue.";
              }
              leaf user-queueoutpir {
                type uint32 {
                  range "0..4294967295";
                }
                units kbit/s;
                config false;
                description
                  "Downstream PIR of a user queue.";
              }
              leaf user-queueoutcir1 {
                type uint32 {
                  range "0..4294967295";
                }
                units kbit/s;
                config false;
                description
                  "User queue downstream CIR 1.";
              }
              leaf user-queueoutpir1 {
                type uint32 {
                  range "0..4294967295";
                }
                units kbit/s;
                config false;
                description
                  "User queue downstream PIR 1.";
              }
              leaf user-queueoutcir2 {
                type uint32 {
                  range "0..4294967295";
                }
                units kbit/s;
                config false;
                description
                  "User queue downstream CIR 2.";
              }
              leaf user-queueoutpir2 {
                type uint32 {
                  range "0..4294967295";
                }
                units kbit/s;
                config false;
                description
                  "User queue downstream PIR 2.";
              }
              leaf user-queueoutcir3 {
                type uint32 {
                  range "0..4294967295";
                }
                units kbit/s;
                config false;
                description
                  "User queue downstream CIR 3.";
              }
              leaf user-queueoutpir3 {
                type uint32 {
                  range "0..4294967295";
                }
                units kbit/s;
                config false;
                description
                  "User queue downstream PIR 3.";
              }
              leaf user-queueoutcir4 {
                type uint32 {
                  range "0..4294967295";
                }
                units kbit/s;
                config false;
                description
                  "User queue downstream CIR 3.";
              }
              leaf user-queueoutpir4 {
                type uint32 {
                  range "0..4294967295";
                }
                units kbit/s;
                config false;
                description
                  "User queue downstream PIR 3.";
              }
              leaf user-queueoutcir5 {
                type uint32 {
                  range "0..4294967295";
                }
                units kbit/s;
                config false;
                description
                  "User queue downstream CIR 5.";
              }
              leaf user-queueoutpir5 {
                type uint32 {
                  range "0..4294967295";
                }
                units kbit/s;
                config false;
                description
                  "User queue downstream PIR 5.";
              }
              leaf domain-carincir {
                type uint32 {
                  range "0..4294967295";
                }
                units kbit/s;
                config false;
                description
                  "User CAR upstream CIR.";
              }
              leaf domain-carinpir {
                type uint32 {
                  range "0..4294967295";
                }
                units kbit/s;
                config false;
                description
                  "User CAR upstream PIR.";
              }
              leaf domain-carincbs {
                type uint32 {
                  range "0..4294967295";
                }
                units Byte;
                config false;
                description
                  "User CAR upstream committed burst size (CBS).";
              }
              leaf domain-carinpbs {
                type uint32 {
                  range "0..4294967295";
                }
                units Byte;
                config false;
                description
                  "User CAR upstream peak burst size (PBS).";
              }
              leaf domain-carincir1 {
                type uint32 {
                  range "0..4294967295";
                }
                units kbit/s;
                config false;
                description
                  "User CAR upstream CIR 1.";
              }
              leaf domain-carinpir1 {
                type uint32 {
                  range "0..4294967295";
                }
                units kbit/s;
                config false;
                description
                  "User CAR upstream PIR 1.";
              }
              leaf domain-carincbs1 {
                type uint32 {
                  range "0..4294967295";
                }
                units Byte;
                config false;
                description
                  "User CAR upstream CBS 1.";
              }
              leaf domain-carinpbs1 {
                type uint32 {
                  range "0..4294967295";
                }
                units Byte;
                config false;
                description
                  "User CAR upstream PBS 1.";
              }
              leaf domain-carincir2 {
                type uint32 {
                  range "0..4294967295";
                }
                units kbit/s;
                config false;
                description
                  "User CAR upstream CIR 2.";
              }
              leaf domain-carinpir2 {
                type uint32 {
                  range "0..4294967295";
                }
                units kbit/s;
                config false;
                description
                  "User CAR upstream PIR 2.";
              }
              leaf domain-carincbs2 {
                type uint32 {
                  range "0..4294967295";
                }
                units Byte;
                config false;
                description
                  "User CAR upstream CBS 2.";
              }
              leaf domain-carinpbs2 {
                type uint32 {
                  range "0..4294967295";
                }
                units Byte;
                config false;
                description
                  "User CAR upstream PBS 2.";
              }
              leaf domain-carincir3 {
                type uint32 {
                  range "0..4294967295";
                }
                units kbit/s;
                config false;
                description
                  "User CAR upstream CIR 3.";
              }
              leaf domain-carinpir3 {
                type uint32 {
                  range "0..4294967295";
                }
                units kbit/s;
                config false;
                description
                  "User CAR upstream PIR 3.";
              }
              leaf domain-carincbs3 {
                type uint32 {
                  range "0..4294967295";
                }
                units Byte;
                config false;
                description
                  "User CAR upstream CBS 3.";
              }
              leaf domain-carinpbs3 {
                type uint32 {
                  range "0..4294967295";
                }
                units Byte;
                config false;
                description
                  "User CAR upstream PBS 3.";
              }
              leaf domain-carincir4 {
                type uint32 {
                  range "0..4294967295";
                }
                units kbit/s;
                config false;
                description
                  "User CAR upstream CIR 4.";
              }
              leaf domain-carinpir4 {
                type uint32 {
                  range "0..4294967295";
                }
                units kbit/s;
                config false;
                description
                  "User CAR upstream PIR 4.";
              }
              leaf domain-carincbs4 {
                type uint32 {
                  range "0..4294967295";
                }
                units Byte;
                config false;
                description
                  "User CAR upstream CBS 4.";
              }
              leaf domain-carinpbs4 {
                type uint32 {
                  range "0..4294967295";
                }
                units Byte;
                config false;
                description
                  "User CAR upstream PBS 4.";
              }
              leaf domain-carincir5 {
                type uint32 {
                  range "0..4294967295";
                }
                units kbit/s;
                config false;
                description
                  "User CAR upstream CIR 5.";
              }
              leaf domain-carinpir5 {
                type uint32 {
                  range "0..4294967295";
                }
                units kbit/s;
                config false;
                description
                  "User CAR upstream PIR 5.";
              }
              leaf domain-carincbs5 {
                type uint32 {
                  range "0..4294967295";
                }
                units Byte;
                config false;
                description
                  "User CAR upstream CBS 5.";
              }
              leaf domain-carinpbs5 {
                type uint32 {
                  range "0..4294967295";
                }
                units Byte;
                config false;
                description
                  "User CAR upstream PBS 5.";
              }
              leaf domain-caroutcir {
                type uint32 {
                  range "0..4294967295";
                }
                units kbit/s;
                config false;
                description
                  "User CAR downstream CIR.";
              }
              leaf domain-caroutpir {
                type uint32 {
                  range "0..4294967295";
                }
                units kbit/s;
                config false;
                description
                  "User CAR downstream PIR.";
              }
              leaf domain-caroutcbs {
                type uint32 {
                  range "0..4294967295";
                }
                units Byte;
                config false;
                description
                  "User CAR downstream CBS.";
              }
              leaf domain-caroutpbs {
                type uint32 {
                  range "0..4294967295";
                }
                units Byte;
                config false;
                description
                  "User CAR downstream PBS.";
              }
              leaf domain-caroutcir1 {
                type uint32 {
                  range "0..4294967295";
                }
                units kbit/s;
                config false;
                description
                  "User CAR downstream CIR 1.";
              }
              leaf domain-caroutpir1 {
                type uint32 {
                  range "0..4294967295";
                }
                units kbit/s;
                config false;
                description
                  "User CAR downstream PIR 1.";
              }
              leaf domain-caroutcbs1 {
                type uint32 {
                  range "0..4294967295";
                }
                units Byte;
                config false;
                description
                  "User CAR downstream CBS 1.";
              }
              leaf domain-caroutpbs1 {
                type uint32 {
                  range "0..4294967295";
                }
                units Byte;
                config false;
                description
                  "User CAR downstream PBS 1.";
              }
              leaf domain-caroutcir2 {
                type uint32 {
                  range "0..4294967295";
                }
                units kbit/s;
                config false;
                description
                  "User CAR downstream CIR 2.";
              }
              leaf domain-caroutpir2 {
                type uint32 {
                  range "0..4294967295";
                }
                units kbit/s;
                config false;
                description
                  "User CAR downstream PIR 2.";
              }
              leaf domain-caroutcbs2 {
                type uint32 {
                  range "0..4294967295";
                }
                units Byte;
                config false;
                description
                  "User CAR downstream CBS 2.";
              }
              leaf domain-caroutpbs2 {
                type uint32 {
                  range "0..4294967295";
                }
                units Byte;
                config false;
                description
                  "User CAR downstream PBS 2.";
              }
              leaf domain-caroutcir3 {
                type uint32 {
                  range "0..4294967295";
                }
                units kbit/s;
                config false;
                description
                  "User CAR downstream CIR 3.";
              }
              leaf domain-caroutpir3 {
                type uint32 {
                  range "0..4294967295";
                }
                units kbit/s;
                config false;
                description
                  "User CAR downstream PIR 3.";
              }
              leaf domain-caroutcbs3 {
                type uint32 {
                  range "0..4294967295";
                }
                units Byte;
                config false;
                description
                  "User CAR downstream CBS 3.";
              }
              leaf domain-caroutpbs3 {
                type uint32 {
                  range "0..4294967295";
                }
                units Byte;
                config false;
                description
                  "User CAR downstream PBS 3.";
              }
              leaf domain-caroutcir4 {
                type uint32 {
                  range "0..4294967295";
                }
                units kbit/s;
                config false;
                description
                  "User CAR downstream CIR 4.";
              }
              leaf domain-caroutpir4 {
                type uint32 {
                  range "0..4294967295";
                }
                units kbit/s;
                config false;
                description
                  "User CAR downstream PIR 4.";
              }
              leaf domain-caroutcbs4 {
                type uint32 {
                  range "0..4294967295";
                }
                units Byte;
                config false;
                description
                  "User CAR downstream CBS 4.";
              }
              leaf domain-caroutpbs4 {
                type uint32 {
                  range "0..4294967295";
                }
                units Byte;
                config false;
                description
                  "User CAR downstream PBS 4.";
              }
              leaf domain-caroutcir5 {
                type uint32 {
                  range "0..4294967295";
                }
                units kbit/s;
                config false;
                description
                  "User CAR downstream CIR 5.";
              }
              leaf domain-caroutpir5 {
                type uint32 {
                  range "0..4294967295";
                }
                units kbit/s;
                config false;
                description
                  "User CAR downstream PIR 5.";
              }
              leaf domain-caroutcbs5 {
                type uint32 {
                  range "0..4294967295";
                }
                units Byte;
                config false;
                description
                  "User CAR downstream CBS 5.";
              }
              leaf domain-caroutpbs5 {
                type uint32 {
                  range "0..4294967295";
                }
                units Byte;
                config false;
                description
                  "User CAR downstream PBS 5.";
              }
              leaf family-carincir {
                type uint32 {
                  range "0..4294967295";
                }
                units kbit/s;
                config false;
                description
                  "Family CAR upstream CIR.";
              }
              leaf family-carinpir {
                type uint32 {
                  range "0..4294967295";
                }
                units kbit/s;
                config false;
                description
                  "Family CAR upstream PIR.";
              }
              leaf family-carincbs {
                type uint32 {
                  range "0..4294967295";
                }
                units Byte;
                config false;
                description
                  "Family CAR upstream CBS.";
              }
              leaf family-carinpbs {
                type uint32 {
                  range "0..4294967295";
                }
                units Byte;
                config false;
                description
                  "Family CAR upstream PBS.";
              }
              leaf family-carincir1 {
                type uint32 {
                  range "0..4294967295";
                }
                units kbit/s;
                config false;
                description
                  "Family CAR upstream CIR 1.";
              }
              leaf family-carinpir1 {
                type uint32 {
                  range "0..4294967295";
                }
                units kbit/s;
                config false;
                description
                  "Family CAR upstream PIR 1.";
              }
              leaf family-carincbs1 {
                type uint32 {
                  range "0..4294967295";
                }
                units Byte;
                config false;
                description
                  "Family CAR upstream CBS 1.";
              }
              leaf family-carinpbs1 {
                type uint32 {
                  range "0..4294967295";
                }
                units Byte;
                config false;
                description
                  "Family CAR upstream PBS 1.";
              }
              leaf family-carincir2 {
                type uint32 {
                  range "0..4294967295";
                }
                units kbit/s;
                config false;
                description
                  "Family CAR upstream CIR 2.";
              }
              leaf family-carinpir2 {
                type uint32 {
                  range "0..4294967295";
                }
                units kbit/s;
                config false;
                description
                  "Family CAR upstream PIR 2.";
              }
              leaf family-carincbs2 {
                type uint32 {
                  range "0..4294967295";
                }
                units Byte;
                config false;
                description
                  "Family CAR upstream CBS 2.";
              }
              leaf family-carinpbs2 {
                type uint32 {
                  range "0..4294967295";
                }
                units Byte;
                config false;
                description
                  "Family CAR upstream PBS 2.";
              }
              leaf family-carincir3 {
                type uint32 {
                  range "0..4294967295";
                }
                units kbit/s;
                config false;
                description
                  "Family CAR upstream CIR 3.";
              }
              leaf family-carinpir3 {
                type uint32 {
                  range "0..4294967295";
                }
                units kbit/s;
                config false;
                description
                  "Family CAR upstream PIR 3.";
              }
              leaf family-carincbs3 {
                type uint32 {
                  range "0..4294967295";
                }
                units Byte;
                config false;
                description
                  "Family CAR upstream CBS 3.";
              }
              leaf family-carinpbs3 {
                type uint32 {
                  range "0..4294967295";
                }
                units Byte;
                config false;
                description
                  "Family CAR upstream PBS 3.";
              }
              leaf family-carincir4 {
                type uint32 {
                  range "0..4294967295";
                }
                units kbit/s;
                config false;
                description
                  "Family CAR upstream CIR 4.";
              }
              leaf family-carinpir4 {
                type uint32 {
                  range "0..4294967295";
                }
                units kbit/s;
                config false;
                description
                  "Family CAR upstream PIR 4.";
              }
              leaf family-carincbs4 {
                type uint32 {
                  range "0..4294967295";
                }
                units Byte;
                config false;
                description
                  "Family CAR upstream CBS 4.";
              }
              leaf family-carinpbs4 {
                type uint32 {
                  range "0..4294967295";
                }
                units Byte;
                config false;
                description
                  "Family CAR upstream PBS 4.";
              }
              leaf family-carincir5 {
                type uint32 {
                  range "0..4294967295";
                }
                units kbit/s;
                config false;
                description
                  "Family CAR upstream CIR 5.";
              }
              leaf family-carinpir5 {
                type uint32 {
                  range "0..4294967295";
                }
                units kbit/s;
                config false;
                description
                  "Family CAR upstream PIR 5.";
              }
              leaf family-carincbs5 {
                type uint32 {
                  range "0..4294967295";
                }
                units Byte;
                config false;
                description
                  "Family CAR upstream CBS 5.";
              }
              leaf family-carinpbs5 {
                type uint32 {
                  range "0..4294967295";
                }
                units Byte;
                config false;
                description
                  "Family CAR upstream PBS 5.";
              }
              leaf family-caroutcir {
                type uint32 {
                  range "0..4294967295";
                }
                units kbit/s;
                config false;
                description
                  "Family CAR downstream CIR.";
              }
              leaf family-caroutpir {
                type uint32 {
                  range "0..4294967295";
                }
                units kbit/s;
                config false;
                description
                  "Family CAR downstream PIR.";
              }
              leaf family-caroutcbs {
                type uint32 {
                  range "0..4294967295";
                }
                units Byte;
                config false;
                description
                  "Family CAR downstream CBS.";
              }
              leaf family-caroutpbs {
                type uint32 {
                  range "0..4294967295";
                }
                units Byte;
                config false;
                description
                  "Family CAR downstream PBS.";
              }
              leaf family-caroutcir1 {
                type uint32 {
                  range "0..4294967295";
                }
                units kbit/s;
                config false;
                description
                  "Family CAR downstream CIR 1.";
              }
              leaf family-caroutpir1 {
                type uint32 {
                  range "0..4294967295";
                }
                units kbit/s;
                config false;
                description
                  "Family CAR downstream PIR 1.";
              }
              leaf family-caroutcbs1 {
                type uint32 {
                  range "0..4294967295";
                }
                units Byte;
                config false;
                description
                  "Family CAR downstream CBS 1.";
              }
              leaf family-caroutpbs1 {
                type uint32 {
                  range "0..4294967295";
                }
                units Byte;
                config false;
                description
                  "Family CAR downstream PBS 1.";
              }
              leaf family-caroutcir2 {
                type uint32 {
                  range "0..4294967295";
                }
                units kbit/s;
                config false;
                description
                  "Family CAR downstream CIR 2.";
              }
              leaf family-caroutpir2 {
                type uint32 {
                  range "0..4294967295";
                }
                units kbit/s;
                config false;
                description
                  "Family CAR downstream PIR 2.";
              }
              leaf family-caroutcbs2 {
                type uint32 {
                  range "0..4294967295";
                }
                units Byte;
                config false;
                description
                  "Family CAR downstream CBS 2.";
              }
              leaf family-caroutpbs2 {
                type uint32 {
                  range "0..4294967295";
                }
                units Byte;
                config false;
                description
                  "Family CAR downstream PBS 2.";
              }
              leaf family-caroutcir3 {
                type uint32 {
                  range "0..4294967295";
                }
                units kbit/s;
                config false;
                description
                  "Family CAR downstream CIR 3.";
              }
              leaf family-caroutpir3 {
                type uint32 {
                  range "0..4294967295";
                }
                units kbit/s;
                config false;
                description
                  "Family CAR downstream PIR 3.";
              }
              leaf family-caroutcbs3 {
                type uint32 {
                  range "0..4294967295";
                }
                units Byte;
                config false;
                description
                  "Family CAR downstream CBS 3.";
              }
              leaf family-caroutpbs3 {
                type uint32 {
                  range "0..4294967295";
                }
                units Byte;
                config false;
                description
                  "Family CAR downstream PBS 3.";
              }
              leaf family-caroutcir4 {
                type uint32 {
                  range "0..4294967295";
                }
                units kbit/s;
                config false;
                description
                  "Family CAR downstream CIR 4.";
              }
              leaf family-caroutpir4 {
                type uint32 {
                  range "0..4294967295";
                }
                units kbit/s;
                config false;
                description
                  "Family CAR downstream PIR 4.";
              }
              leaf family-caroutcbs4 {
                type uint32 {
                  range "0..4294967295";
                }
                units Byte;
                config false;
                description
                  "Family CAR downstream CBS 4.";
              }
              leaf family-caroutpbs4 {
                type uint32 {
                  range "0..4294967295";
                }
                units Byte;
                config false;
                description
                  "Family CAR downstream PBS 4.";
              }
              leaf family-caroutcir5 {
                type uint32 {
                  range "0..4294967295";
                }
                units kbit/s;
                config false;
                description
                  "Family CAR downstream CIR 5.";
              }
              leaf family-caroutpir5 {
                type uint32 {
                  range "0..4294967295";
                }
                units kbit/s;
                config false;
                description
                  "Family CAR downstream PIR 5.";
              }
              leaf family-caroutcbs5 {
                type uint32 {
                  range "0..4294967295";
                }
                units Byte;
                config false;
                description
                  "Family CAR downstream CBS 5.";
              }
              leaf family-caroutpbs5 {
                type uint32 {
                  range "0..4294967295";
                }
                units Byte;
                config false;
                description
                  "Family CAR downstream PBS 5.";
              }            
            }
          }
        }
        container access-user-flow-statistic-info {
          config false;
          description
            "Statistics of access user flow statistic.";
          leaf acct-flw {
            type uint32 {
              range "0..4294967295";
            }
            config false;
            description
              "Total (upstream and downstream) rate for sending real-time accounting packets.";
          }
          leaf acct-byt-flg {
            type bras-user-manage-byte-type;
            config false;
            description
              "Total real-time rate unit.";
          }
          leaf acct-up-flw {
            type uint32 {
              range "0..4294967295";
            }
            config false;
            description
              "Upstream rate for sending real-time accounting packets.";
          }
          leaf acct-up-byt-flg {
            type bras-user-manage-byte-type;
            config false;
            description
              "Upstream real-time rate unit.";
          }
          leaf acct-dn-flw {
            type uint32 {
              range "0..4294967295";
            }
            config false;
            description
              "Downstream rate for sending real-time accounting packets.";
          }
          leaf acct-dn-byt-flg {
            type bras-user-manage-byte-type;
            config false;
            description
              "Downstream real-time rate.";
          }
          leaf flw-inc-l2-flg {
            type bras-user-manage-common-enable-type;
            config false;
            description
              "Traffic information contains Layer 2 headers.";
          }
          leaf flw-up-stat-flg {
            type bras-user-manage-common-enable-type;
            config false;
            description
              "Upstream traffic statistics collection is enabled.";
          }
          leaf flw-dn-stat-flg {
            type bras-user-manage-common-enable-type;
            config false;
            description
              "Downstream traffic statistics collection is enabled.";
          }
          leaf ip4-flw-up-st-pkt-hi {
            type uint32 {
              range "0..4294967295";
            }
            units packet;
            config false;
            description
              "Number of upstream packets (most significant bits).";
          }
          leaf ip4-flw-up-st-pkt-lo {
            type uint32 {
              range "0..4294967295";
            }
            units packet;
            config false;
            description
              "Number of upstream packets (least significant bits).";
          }
          leaf ip4-flw-up-st-byt-hi {
            type uint32 {
              range "0..4294967295";
            }
            units Byte;
            config false;
            description
              "Number of upstream bytes (most significant bits).";
          }
          leaf ip4-flw-up-st-byt-lo {
            type uint32 {
              range "0..4294967295";
            }
            units Byte;
            config false;
            description
              "Number of upstream bytes (least significant bits).";
          }
          leaf ip4-flw-dn-st-pkt-hi {
            type uint32 {
              range "0..4294967295";
            }
            units packet;
            config false;
            description
              "Number of downstream packets (most significant bits).";
          }
          leaf ip4-flw-dn-st-pkt-lo {
            type uint32 {
              range "0..4294967295";
            }
            units packet;
            config false;
            description
              "Number of downstream packets (least significant bits).";
          }
          leaf ip4-flw-dn-st-byt-hi {
            type uint32 {
              range "0..4294967295";
            }
            units Byte;
            config false;
            description
              "Number of downstream bytes (most significant bits).";
          }
          leaf ip4-flw-dn-st-byt-lo {
            type uint32 {
              range "0..4294967295";
            }
            units Byte;
            config false;
            description
              "Number of downstream bytes (least significant bits).";
          }
          leaf l2-flw-up-st-pkt-hi {
            type uint32 {
              range "0..4294967295";
            }
            units packet;
            config false;
            description
              "Number of L2 upstream packets (most significant bits).";
          }
          leaf l2-flw-up-st-pkt-lo {
            type uint32 {
              range "0..4294967295";
            }
            units packet;
            config false;
            description
              "Number of L2 upstream packets (least significant bits).";
          }
          leaf l2-flw-up-st-byt-hi {
            type uint32 {
              range "0..4294967295";
            }
            units Byte;
            config false;
            description
              "Number of L2 upstream bytes (most significant bits).";
          }
          leaf l2-flw-up-st-byt-lo {
            type uint32 {
              range "0..4294967295";
            }
            units Byte;
            config false;
            description
              "Number of L2 upstream bytes (least significant bits).";
          }
          leaf l2-flw-dn-st-pkt-hi {
            type uint32 {
              range "0..4294967295";
            }
            units packet;
            config false;
            description
              "Number of L2 downstream packets (most significant bits).";
          }
          leaf l2-flw-dn-st-pkt-lo {
            type uint32 {
              range "0..4294967295";
            }
            units packet;
            config false;
            description
              "Number of L2 downstream packets (least significant bits).";
          }
          leaf l2-flw-dn-st-byt-hi {
            type uint32 {
              range "0..4294967295";
            }
            units Byte;
            config false;
            description
              "Number of L2 downstream bytes (most significant bits).";
          }
          leaf l2-flw-dn-st-byt-lo {
            type uint32 {
              range "0..4294967295";
            }
            units Byte;
            config false;
            description
              "Number of L2 downstream bytes (least significant bits).";
          }
          leaf ip6-flw-up-st-pkt-hi {
            type uint32 {
              range "0..4294967295";
            }
            units packet;
            config false;
            description
              "Number of IPv6 upstream packets (most significant bits).";
          }
          leaf ip6-flw-up-st-pkt-lo {
            type uint32 {
              range "0..4294967295";
            }
            units packet;
            config false;
            description
              "Number of IPv6 upstream packets (least significant bits).";
          }
          leaf ip6-flw-up-st-byt-hi {
            type uint32 {
              range "0..4294967295";
            }
            units Byte;
            config false;
            description
              "Number of IPv6 upstream bytes (most significant bits).";
          }
          leaf ip6-flw-up-st-byt-lo {
            type uint32 {
              range "0..4294967295";
            }
            units Byte;
            config false;
            description
              "Number of IPv6 upstream bytes (least significant bits).";
          }
          leaf ip6-flw-dn-st-pkt-hi {
            type uint32 {
              range "0..4294967295";
            }
            units packet;
            config false;
            description
              "Number of IPv6 downstream packets (most significant bits).";
          }
          leaf ip6-flw-dn-st-pkt-lo {
            type uint32 {
              range "0..4294967295";
            }
            units packet;
            config false;
            description
              "Number of IPv6 downstream packets (least significant bits).";
          }
          leaf ip6-flw-dn-st-byt-hi {
            type uint32 {
              range "0..4294967295";
            }
            units Byte;
            config false;
            description
              "Number of IPv6 downstream bytes (most significant bits).";
          }
          leaf ip6-flw-dn-st-byt-lo {
            type uint32 {
              range "0..4294967295";
            }
            units Byte;
            config false;
            description
              "Number of IPv6 downstream bytes (least significant bits).";
          }
          leaf mc-flw-dn-st-pkt-hi {
            type uint32 {
              range "0..4294967295";
            }
            units packet;
            config false;
            description
              "Number of multicast downstream packets (most significant bits).";
          }
          leaf mc-flw-dn-st-pkt-lo {
            type uint32 {
              range "0..4294967295";
            }
            units packet;
            config false;
            description
              "Number of multicast downstream packets (least significant bits).";
          }
          leaf mc-flw-dn-st-byt-hi {
            type uint32 {
              range "0..4294967295";
            }
            units Byte;
            config false;
            description
              "Number of multicast downstream bytes (most significant bits).";
          }
          leaf mc-flw-dn-st-byt-lo {
            type uint32 {
              range "0..4294967295";
            }
            units Byte;
            config false;
            description
              "Number of multicast downstream bytes (least significant bits).";
          }
          container access-discarded-stream-infos {
            config false;
            description
              "List of the access discarded stream.";
            list access-discarded-stream-info {
              key "stream-type queue-type direction";
              config false;
              description
                "Statistics of access discarded stream.";
              leaf stream-type {
                type enumeration {
                  enum "local" {
                    value 0;
                    description
                      "Local.";
                  }
                  enum "remote" {
                    value 1;
                    description
                      "Remote.";
                  }
                }
                config false;
                description
                  "Type of stream.";
              }
              leaf queue-type {
                type enumeration {
                  enum "be" {
                    value 0;
                    description
                      "Be.";
                  }
                  enum "af1" {
                    value 1;
                    description
                      "Af1.";
                  }
                  enum "af2" {
                    value 2;
                    description
                      "Af2.";
                  }
                  enum "af3" {
                    value 3;
                    description
                      "Af3.";
                  }
                  enum "af4" {
                    value 4;
                    description
                      "Af4.";
                  }
                  enum "ef" {
                    value 5;
                    description
                      "Ef.";
                  }
                  enum "cs6" {
                    value 6;
                    description
                      "Cs6.";
                  }
                  enum "cs7" {
                    value 7;
                    description
                      "Cs7.";
                  }
                }
                config false;
                description
                  "Type of queue.";
              }
              leaf direction {
                type enumeration {
                  enum "down" {
                    value 0;
                    description
                      "Down.";
                  }
                  enum "up" {
                    value 1;
                    description
                      "Up.";
                  }
                }
                config false;
                description
                  "Direction of stream.";
              }
              leaf flow-packet-high {
                type uint32 {
                  range "0..4294967295";
                }
                units packet;
                config false;
                description
                  "Number of discarded packets (most significant bits).";
              }
              leaf flow-packet-low {
                type uint32 {
                  range "0..4294967295";
                }
                units packet;
                config false;
                description
                  "Number of discarded packets (least significant bits).";
              }
              leaf flow-byte-high {
                type uint32 {
                  range "0..4294967295";
                }
                units Byte;
                config false;
                description
                  "Number of discarded bytes (most significant bits).";
              }    
              leaf flow-byte-low {
                type uint32 {
                  range "0..4294967295";
                }
                units Byte;
                config false;
                description
                  "Number of discarded bytes (least significant bits).";
              }            
            }
          }
        }
        container access-user-dslam-info {
          config false;
          description
            "Statistics of access user dslam.";
          leaf l2cp-circuit-id {
            type string {
              length "1..200";
            }
            config false;
            description
              "DSLAM line ID.";
          }
          leaf l2cp-remote-id {
            type string {
              length "1..200";
            }
            config false;
            description
              "DSLAM remote ID.";
          }
          leaf actual-data-rate-upstream {
            type uint32 {
              range "0..4294967295";
            }
            units kbit/s;
            config false;
            description
              "Actual upstream data rate of the DSLAM.";
          }
          leaf actual-data-rate-downstream {
            type uint32 {
              range "0..4294967295";
            }
            units kbit/s;
            config false;
            description
              "Actual downstream data rate of the DSLAM.";
          }
          leaf minimum-data-rate-upstream {
            type uint32 {
              range "0..4294967295";
            }
            units kbit/s;
            config false;
            description
              "Minimum upstream data rate of the DSLAM.";
          }
          leaf minimum-data-rate-downstream {
            type uint32 {
              range "0..4294967295";
            }
            units kbit/s;
            config false;
            description
              "Minimum downstream data rate of the DSLAM.";
          }
          leaf attainable-data-rate-upstream {
            type uint32 {
              range "0..4294967295";
            }
            units kbit/s;
            config false;
            description
              "Attainable upstream data rate of the DSLAM.";
          }
          leaf attainable-data-rate-downstream {
            type uint32 {
              range "0..4294967295";
            }
            units kbit/s;
            config false;
            description
              "Attainable downstream data rate of the DSLAM.";
          }
          leaf maximum-data-rate-upstream {
            type uint32 {
              range "0..4294967295";
            }
            units kbit/s;
            config false;
            description
              "Maximum upstream data rate of the DSLAM.";
          }
          leaf maximum-data-rate-downstream {
            type uint32 {
              range "0..4294967295";
            }
            units kbit/s;
            config false;
            description
              "Maximum downstream data rate of the DSLAM.";
          }
          leaf minimum-data-rate-up-low-power {
            type uint32 {
              range "0..4294967295";
            }
            units kbit/s;
            config false;
            description
              "Minimum upstream data rate in the low power state of the DSLAM.";
          }
          leaf minimum-data-rate-down-low-power {
            type uint32 {
              range "0..4294967295";
            }
            units kbit/s;
            config false;
            description
              "Maximum downstream data rate in the low power state of the DSLAM.";
          }
          leaf maximum-int-delay-upstream {
            type uint32 {
              range "0..4294967295";
            }
            units s;
            config false;
            description
              "Maximum upstream delay of the DSLAM.";
          }
          leaf maximum-int-delay-downstream {
            type uint32 {
              range "0..4294967295";
            }
            units s;
            config false;
            description
              "Maximum downstream delay of the DSLAM.";
          }
          leaf actual-int-delay-upstream {
            type uint32 {
              range "0..4294967295";
            }
            units s;
            config false;
            description
              "Actual upstream delay of the DSLAM.";
          }
          leaf actual-int-delay-downstream {
            type uint32 {
              range "0..4294967295";
            }
            units s;
            config false;
            description
              "Actual downstream delay of the DSLAM.";
          }
          leaf access-loop-encapsulation {
            type string {
              length "1..10";
            }
            config false;
            description
              "DSLAM encapsulation information.";
          }        
        }
        container access-user-l2tp-or-cu-info {
          config false;
          description
            "Statistics of access user l2tp or cu.";
          leaf up-id {
            type int32 {
              range "1024..2023 | 2048..3047 | 3072..4071 | 4096..5095";
            }
            config false;
            description
              "UP ID.";
          }
          leaf l2tp-peer {
            type bras-user-manage-l2tp-peer-type;
            config false;
            description
              "L2TP peer type.";
          }
          leaf lac-tnl-id {
            type uint32 {
              range "0..4294967295";
            }
            config false;
            description
              "Index of a LAC tunnel.";
          }
          leaf lac-session-id {
            type uint32 {
              range "0..4294967295";
            }
            config false;
            description
              "Index of a LAC session.";
          }
          leaf l2tp-grp-name {
            type string {
              length "1..32";
            }
            config false;
            description
              "Name of an L2TP group on the LAC.";
          }
          leaf l2tp-grp-rds-flg {
            type bras-user-manage-common-enable-type;
            config false;
            description
              "LAC L2TP group name delivered by the RADIUS server.";
          }
          leaf lns-tnl-id {
            type uint32 {
              range "0..4294967295";
            }
            config false;
            description
              "Index of an LNS tunnel.";
          }
          leaf lns-session-id {
            type uint32 {
              range "0..4294967295";
            }
            config false;
            description
              "Index of an LNS session.";
          }
          leaf lns-slot {
            type string {
              length "1..63";
            }
            config false;
            description
              "LNS slot.";
          }
          leaf l2tp-tnl-sip {
            type inet:ipv4-address-no-zone;
            config false;
            description
              "Source address of an L2TP tunnel.";
          }
          leaf l2tp-tnl-auth-id {
            type string {
              length "1..253";
            }
            config false;
            description
              "LAC-side tunnel name.";
          }
          leaf up-rui-prf-name {
            type string {
              length "1..33";
            }
            config false;
            description
              "Name of a UP hot standby policy template.";
          }
          leaf cu-master-ifname {
            type string {
              length "1..64";
            }
            config false;
            description
              "Master user access interface in CU separation UP hot standby scenarios.";
          }
          leaf cu-slave-ifname {
            type string {
              length "1..64";
            }
            config false;
            description
              "Backup user access interface in CU separation UP hot standby scenarios.";
          }    
        }     
        container access-user-edsg-infos {
          config false;
          description
            "List of EDSG information delivered through authentication response packets.";
          list access-user-edsg-info{
            key "msiserviceindex";
            config false;
            description
              "Statistics of the EDSG service.";
            leaf msiserviceindex {
              type uint16;
              config false;
              description
                "EDSG service information index.";
            }
            leaf active-flag {
              type bras-user-manage-common-enable-type;
              config false;
              description
                "EDSG service information activation.";
            }
            leaf service-name {
              type string {
                length "1..200";
              }
              config false;
              description
                "Name of an EDSG service.";
            }
          }
        }
        container access-user-daa-policy-info {
          config false;
          description
            "Statistics of access user daa policy.";
          leaf sub-redir-key {
            type string {
              length "1..32";
            }
            config false;
            description
              "Keyword of the Subscription-Id attribute.";
          }
          leaf sub-id {
            type string {
              length "1..253";
            }
            config false;
            description
              "Subscription ID.";
          }
          leaf sub-id-rds-flg {
            type bras-user-manage-common-enable-type;
            config false;
            description
              "User subscription ID delivered by the RADIUS server.";
          }
          leaf daa-policy-name {
            type string {
              length "1..64";
            }
            config false;
            description
              "DAA service information.";
          }
          leaf daa-policy-name-lv1 {
            type string {
              length "1..64";
            }
            config false;
            description
              "Information about the activated DAA service (LV1).";
          }
          leaf daa-policy-name-lv2 {
            type string {
              length "1..64";
            }
            config false;
            description
              "Information about the activated DAA service (LV2).";
          }
          leaf daa-policy-name-lv3 {
            type string {
              length "1..64";
            }
            config false;
            description
              "Information about the activated DAA service (LV3).";
          }
          leaf daa-policy-name-lv4 {
            type string {
              length "1..64";
            }
            config false;
            description
              "Information about the activated DAA service (LV4).";
          }
          leaf daa-policy-name-lv5 {
            type string {
              length "1..64";
            }
            config false;
            description
              "Information about the activated DAA service (LV5).";
          }
          leaf daa-policy-name-lv6 {
            type string {
              length "1..64";
            }
            config false;
            description
              "Information about the activated DAA service (LV6).";
          }
          leaf daa-policy-name-lv7 {
            type string {
              length "1..64";
            }
            config false;
            description
              "Information about the activated DAA service (LV7).";
          }
          leaf daa-policy-name-lv8 {
            type string {
              length "1..64";
            }
            config false;
            description
              "Information about the activated DAA service (LV8).";
          }        
        }
      }
    }
    container slot-access-user-statistics {
      config false;
      description
        "List of the users with the ID of the slot.";
      list slot-access-user-statistic {
        key "slot-id user-type";
        description
          "Statistics of users with the ID of the slot.";
        leaf slot-id {
          type int32 {
            range "0..509600";
          }
          description
            "Slot ID.";
        }
        leaf user-type {
          type bras-user-manage-user-type;
          description
            "User type.";
        }
        leaf slot {
          type string {
              length "1..32";
          }
          description
            "This node applies to scenarios where the vBRAS-UP or device has been enabled with virtual access. In this case, the slot ID is in the 1024/1 or clc1/2 format.";
        }
        leaf user-number {
          type int32 {
            range "0..256000";
          }
          description
            "User number.";
        }
      }
    }
    container access-user-resource-usage {
      config false;
      description
        "Statistics of the user resource usage of the main control board and interface boards.";
      container mpu {
        config false;
        description
          "Statistics of the user usage of the main control board.";
        uses access-user-resource-usage;
      }
      container license {
        config false;
        description
          "Statistics of the user usage of the license.";
        uses access-user-resource-usage;
      }
      container slots {
        config false;
        description
          "List of the user resource usage of the interface board.";
        list slot {
          key "slot-id";
          config false;
          description
            "Statistics of the user resource usage of the interface board.";
          leaf slot-id {
            type string {
              length "1..63";
            }
            config false;
            description
              "Slot Id.";
          }
          uses access-user-resource-usage;
        }
      }
    }
    container domain-max-online-user-statistics {
      config false;
      description
        "List of the domain max online users on the history.";
      list domain-max-online-user-statistic {
        key "domain-name";
        description
          "Statistics of a domain max online users on the history.";
        leaf domain-name {
          type string {
            length "1..64";
          }
          description
            "Doamin name.";
        }
        uses domain-max-online-user-info-type;
      }
    }
    container max-online-user-statistic {
      config false;
      description
        "Statistics of the max online users on the history.";
      uses max-online-user;
      container slots {
        description
          "List of the slot max online users on the history.";
        list slot {
          key "slot-id";
          description
            "Statistics of a slot max online users on the history.";
          leaf slot-id {
            type string {
              length "1..16";
            }
            description
              "Slot id.";
          }
          uses max-online-user-by-slot;
        }
      }
      container ups {
        description
          "List of the up max online users on the history.";
        list up {
          key "up-id";
          description
            "Statistics of a up max online users on the history.";
          leaf up-id {
            type uint32 {
              range "0 | 1024..2023 | 2048..3047 | 3072..4071 | 4096..5095";
            }
            description
              "ID of the UP connected to a vBRAS-CP. If the device is not a vBRAS-CP or no UP is specified, the value of this object is set to 0.";
          }
          uses max-online-user-by-slot;
        }
      }
    }
    container cu-max-online-user-statistics {
      config false;
      description
        "List of the max online users on the history.";
      list cu-max-online-user-statistic {
        key "upmng-instance";
        description
          "Statistics of the max online users on the history.";
        leaf upmng-instance {
          type string {
            length "1..15";
          }
          description
            "UPMNG instance.";
        }
        uses max-online-user;
      }
    }
    container aaa-call-rate {
      config false;
      description
        "Statistics of call put-through rates.";
      leaf total-connect-number {
        type uint32;
        description
          "The number of all access users.";
      }
      leaf total-success-number {
        type uint32;
        description
          "The number of all success access users.";
      }
      leaf total-lcp-fail-number {
        type uint32;
        description
          "The number of all fail access ppp users during LCP.";
      }
      leaf total-authen-fail-number {
        type uint32;
        description
          "The number of all authenfail access ppp users.";
      }
      leaf total-ncp-fail-number {
        type uint32;
        description
          "The number of all authenfail access ppp users.";
      }
      leaf total-ip-alloc-fail-number {
        type uint32;
        description
          "The number of all authenfail access ppp users.";
      }
      leaf total-other-ppp-fail-number {
        type uint32;
        description
          "The number of all authenfail access ppp user.";
      }
      leaf total-web-connect-number {
        type uint32;
        description
          "The number of access all web and fast user.";
      }
      leaf total-success-web-connect-number {
        type uint32;
        description
          "The number of all success access web and fast user.";
      }
      leaf total-bind-connect-number {
        type uint32;
        description
          "The number of access all bind user.";
      }
      leaf total-success-bind-connect-number {
        type uint32;
        description
          "The number of all success access bind user.";
      }
      leaf total-ppp-connect-num {
        type uint32;
        description
          "The number of all access users.";
      }
      leaf total-ppp-success-num {
        type uint32;
        description
          "The number of all success access ppp users.";
      }
      leaf total-dot1x-connect-num {
        type uint32;
        description
          "The number of access all dot1x user.";
      }
      leaf total-success-dot1x-num {
        type uint32;
        description
          "The number of all success access dot1x user.";
      }
      leaf ppp-rate {
        type string {
          length "1..7";
        }
        description
          "The rate of ppp users.";
      }
      leaf web-rate {
        type string {
          length "1..7";
        }
        description
          "The rate of web and fast users.";
      }
      leaf dot1x-rate {
        type string {
          length "1..7";
        }
        description
          "The rate of dot1x users.";
      }
      leaf bind-rate {
        type string {
          length "1..7";
        }
        description
          "The rate of bind users.";
      }
      leaf total-rate {
        type string {
          length "1..7";
        }
        description
          "The rate of total users.";
      }
    }
    container aaa-online-fail-or-offline-statistics {
      config false;
      description
        "List of MAC addresses or interfaces (interface IDs+VLAN IDs) by the number of login failure/logout records.";
      list aaa-online-fail-or-offline-statistic {
        key "record-type record-order top-number";
        description
          "Statistics of MAC addresses or interfaces (interface IDs+VLAN IDs) by the number of login failure/logout records.";
        uses online-fail-or-offline-statistic-info;
      }
    }
    container aaa-online-fail-or-offline-cu-statistics {
      config false;
      description
        "List of MAC addresses or interfaces (interface IDs+VLAN IDs) by the number of login failure/logout records.";
      list aaa-online-fail-or-offline-cu-statistic {
        key "upmng-instance record-type record-order top-number";
        description
          "Statistics of MAC addresses or interfaces (interface IDs+VLAN IDs) by the number of login failure/logout records.";
        leaf upmng-instance {
          type string {
            length "1..15";
          }
          description
            "UPMNG instance name.";
        }
        uses online-fail-or-offline-statistic-info;
      }
    }
    container aaa-statistics {
      config false;
      description
        "Statistics of AAA statistical.";
      leaf total-online-number {
        type uint32;
        description
          "Indicates the number of all online users.";
      }
      leaf total-pppoe-online-number {
        type uint32;
        description
          "Indicates the number of PPPoE online users.";
      }
      leaf total-pppoa-online-number {
        type uint32;
        description
          "Indicates the number of PPPoA online users.";
      }
      leaf total-ftp-online-number {
        type uint32;
        description
          "Indicates the number of FTP online users.";
      }
      leaf total-ssh-online-number {
        type uint32;
        description
          "Indicates the number of SSH online users.";
      }
      leaf total-telnet-online-number {
        type uint32;
        description
          "Indicates the number of telnet online users.";
      }
      leaf total-vlan-online-number {
        type uint32;
        description
          "Indicates the number of IPoE online users.";
      }
      leaf historic-max-online-number {
        type uint32;
        description
          "Maximum number of concurrent online users in the history.";
      }
      leaf max-pppoe-online-number {
        type uint32;
        description
          "Maximum number of PPPOE online users.";
      }
      leaf total-portal-user-number {
        type uint32;
        description
          "Indicates the number of portal server online users.";
      }
      leaf max-portal-user-number {
        type uint32;
        description
          "Maximum number of portal server online users.";
      }
      leaf total-ipv4-online-number {
        type uint32;
        description
          "Number of IPv4 access users.";
      }
      leaf total-ipv6-online-number {
        type uint32;
        description
          "Number of IPv6 access users.";
      }
      leaf total-dual-stack-online-number {
        type uint32;
        description
          "Number of dual-stack access users.";
      }
      leaf total-ipv4-flow-down-byte {
        type uint64;
        units Byte;
        description
          "Number of IPv4 flow down byte.";
      }
      leaf total-ipv4-flow-down-packet {
        type uint64;
        description
          "Number of IPv4 flow down packet.";
      }
      leaf total-ipv4-flow-up-byte {
        type uint64;
        units Byte;
        description
          "Number of IPv4 flow up byte.";
      }
      leaf total-ipv4-flow-up-packet {
        type uint64;
        description
          "Number of IPv4 flow up packet.";
      }
      leaf total-ipv6-flow-down-byte {
        type uint64;
        units Byte;
        description
          "Number of IPv6 flow down byte.";
      }
      leaf total-ipv6-flow-down-packet {
        type uint64;
        description
          "Number of IPv6 flow down packet.";
      }
      leaf total-ipv6-flow-up-byte {
        type uint64;
        units Byte;
        description
          "Number of IPv6 flow up byte.";
      }
      leaf total-ipv6-flow-up-packet {
        type uint64;
        description
          "Number of IPv6 flow up packet.";
      }
      leaf historic-max-online-acct-ready-num {
        type uint32;
        description
          "Time when the maximum number of users with correct accounting records were online.";
      }
      leaf public-lac-user-number {
        type uint32;
        description
          "Number of public Lac users.";
      }
      leaf historic-max-rui-online-local-num {
        type uint32;
        description
          "Maximum number of local online users in the history, including common users and RUI users.";
      }
      leaf historic-max-rui-online-remote-num {
        type uint32;
        description
          "Maximum number of remote online users in the history, including common users and RUI users.";
      }
      leaf total-lac-online-number {
        type uint32;
        description
          "Number of lac access users.";
      }
      leaf total-lns-online-number {
        type uint32;
        description
          "Number of lns access users.";
      }
      leaf total-wireless-online-number {
        type uint32;
        description
          "Number of wireless access users.";
      }
      leaf total-wired-online-number {
        type uint32;
        description
          "Number of wired access users.";
      }
      leaf historic-max-online-num-date {
        type string {
          length "1..32";
        }
        description
          "The number of historical peak time.";
      }
      leaf total-lease-online-number {
        type uint32;
        description
          "Display the number of online leased line users.";
      }
      leaf total-tunnel-online-number {
        type uint32;
        description
          "Display the number of online tunnel users.";
      }
      leaf total-ppp-online-number {
        type uint32;
        description
          "Display the number of online PPP users.";
      }
    }
    container access-user-extend-states {
      config false;
      description
        "List of the access extend.";
      list access-user-extend-state {
        key "access-index";
        description
          "Statistics of access extend.";
        leaf access-index {
          type uint32 {
            range "0..2147483647";
          }
          description
            "Access user index.";
        }
        leaf user-group {
          type int32 {
            range "0..65535";
          }
          description
            "User group.";
        }
        leaf authentication-state {
          type int32 {
            range "1..4";
          }
          description
            "This object indicates the status of the authentication state machine.";
        }
        leaf authorization-state {
          type int32 {
            range "1..4";
          }
          description
            "This object indicates the status of the authorization state machine.";
        }
        leaf accounting-state {
          type int32 {
            range "1..7";
          }
          description
            "This object indicates the status of the accounting state machine.";
        }
        leaf domain-name {
          type string {
            length "1..64";
          }
          description
            "This object indicates the user domain.";
          ext:support-filter "true";
        }
        leaf idle-start-time {
          type int32 {
            range "0..120";
          }
          description
            "This object indicates the idle start time.";
        }
        leaf account-session-id {
          type string {
            length "0..44";
          }
          description
            "This object indicates the accounting session ID.";
        }
        leaf access-start-account-time {
          type string {
            length "1..23";
          }
          description
            "This object indicates the start time of accounting.";
        }
        leaf access-normal-radius-server-group {
          type string {
            length "1..32";
          }
          description
            "This object indicates the name of the common authentication and accounting RADIUS server group.
             If the value is '--', it indicates that no name is configured.";
        }
        leaf domain-account-copy-radius-sever {
          type string {
            length "1..32";
          }
          description
            "This object indicates the name of the accounting copy RADIUS server group in a domain.
             If the value is '--', it indicates that no name is configured.";
        }
        leaf interface-account-copy-radius-sever {
          type string {
            length "1..32";
          }
          description
            "This object indicates the name of the accounting copy RADIUS server group on an interface.
             If the value is '--', it indicates that no name is configured.";
        }
        leaf access-current-authen-place {
          type enumeration {
            enum "none" {
              value 0;
              description
                "Allows users' access without authentication.";
            }
            enum "local" {
              value 1;
              description
                "Authenticates users locally.";
            }
            enum "radius" {
              value 2;
              description
                "Authenticates users through a RADIUS server.";
            }
            enum "tacacs" {
              value 3;
              description
                "Authenticates users through an TACACS server.";
            }
          }
          description
            "This object indicates current authentication place.";
        }
        leaf access-action-flag {
          type bras-user-manage-access-action-flag;
          description
            "Action flag.";
        }
        leaf access-auth-type {
          type bras-user-manage-access-auth-type;
          description
            "This object indicates the user authentication type.";
        }
        leaf access-type {
          type bras-user-manage-extend-access-type;
          description
            "The access type.";
          ext:support-filter "true";
        }
        leaf access-total-online-time {
          type uint32;
          units s;
          description
            "The user total online time.";
        }
        leaf resource-insufficient-inbound {
          type int32 {
            range "0..2147483647";
          }
          config false;
          description
            "Inbound result of insufficient resource (If resource is insufficient, set the result to 1, else 0).";
        }
        leaf resource-insufficient-outbound {
          type int32 {
            range "0..2147483647";
          }
          config false;
          description
            "Outbound result of insufficient resource (If resource is insufficient, set the result to 1, else 0).";
        }
      }
    }
    container online-fail-record-statistic {
      config false;
      description
        "Statistics of the online fail number of DHCP users.";
      leaf dhcpv4-online-failures {
        type uint32;
        description
          "The online fail number of DHCPv4 users.";
      }
      leaf dhcpv6-online-failures {
        type uint32;
        description
          "The online fail number of DHCPv6 users.";
      }
    }
    container rate-limit-states {
      config false;
      description
        "List of the traffic statistics for online users.";
      list rate-limit-state {
        key "direction rate-type";
        description
          "Statistics of online users traffic.";
        leaf direction {
          type enumeration {
            enum "inbound" {
              value 1;
              description
                "Inbound direction.";
            }
            enum "outbound" {
              value 2;
              description
                "Outbound direction.";
            }
          }
          description
            "The direction of rate.";
        }
        leaf rate-type {
          type int32;
          description
            "The type of rate.";
        }
        leaf rate-peak {
          type int32;
          description
            "The peak of rate.";
        }
        leaf rate-average {
          type int32;
          description
            "The average of rate.";
        }
        leaf users {
          type int32;
          description
            "The users number.";
        }
        leaf percent {
          type int32 {
            range "0..100";
          }
          description
            "The percent of rate.";
        }
      }
    }
    container access-packet-discard-statistics {
      config false;
      description
        "List of MAC-spoofing-dropped and URPF-dropped packets on a specified interface or board. The statistics can be collected based on user types.";
      list access-packet-discard-statistic {
        key "slot-id interface-name discard-type";
        description
          "Statistics of MAC-spoofing-dropped and URPF-dropped packets on a specified interface or board. The statistics can be collected based on user types.";
        leaf slot-id {
          type string {
            length "1..15";
          }
          description
            "ID of an available slot.";
        }
        leaf interface-name {
          type string {
            length "1..49";
          }
          description
            "Name of an interface.";
        }
        leaf discard-type {
          type enumeration {
            enum "mac-spoofing" {
              value 1;
              description
                "Packet discarding type:mac-spoofing.";
            }
            enum "urpf" {
              value 2;
              description
                "Packet discarding type:Urpf.";
            }
          }
          description
            "Packet discarding type.";
        }
        leaf pppoe-ipv4-packets-high {
          type uint32 {
            range "0..4294967295";
          }
          description
            "The most significant 32 bits of the number of IPv4 packets discarded by pppoev4 users.";
        }
        leaf pppoe-ipv4-packets-low {
          type uint32 {
            range "0..4294967295";
          }
          description
            "The least significant 32 bits of the number of IPv4 packets discarded by pppoev4 users.";
        }
        leaf pppoe-ipv6-packets-high {
          type uint32 {
            range "0..4294967295";
          }
          description
            "The most significant 32 bits of the number of IPv6 packets discarded by pppoev6 users.";
        }
        leaf pppoe-ipv6-packets-low {
          type uint32 {
            range "0..4294967295";
          }
          description
            "The least significant 32 bits of the number of IPv6 packets discarded by pppoev6 users.";
        }
        leaf ipoe-ipv4-packets-high {
          type uint32 {
            range "0..4294967295";
          }
          description
            "The most significant 32 bits of the number of IPv4 packets discarded by ipoe IPv4 users.";
        }
        leaf ipoe-ipv4-packets-low {
          type uint32 {
            range "0..4294967295";
          }
          description
            "The least significant 32 bits of the number of IPv4 packets discarded by ipoe IPv4 users.";
        }
        leaf ipoe-ipv6-packets-high {
          type uint32 {
            range "0..4294967295";
          }
          description
            "The most significant 32 bits of the number of IPv6 packets discarded by ipoe IPv6 users.";
        }
        leaf ipoe-ipv6-packets-low {
          type uint32 {
            range "0..4294967295";
          }
          description
            "The least significant 32 bits of the number of IPv4 packets discarded by ipoe IPv6 users.";
        }
      }
    }
    container domain-statistics {
      config false;
      description
        "List of the domain.";
      list domain-statistic {
        key "domain-name";
        description
          "Statistics of the domain.";
        leaf domain-name {
          type string {
            length "1..64";
          }
          description
            "Domain name.";
        }
        leaf accessed-number {
          type int32 {
            range "0..2147483647";
          }
          description
            "Accessed Number.";
        }
        leaf online-number {
          type int32 {
            range "0..2147483647";
          }
          description
            "Online number.";
        }
        leaf online-ppp-user {
          type int32 {
            range "0..2147483647";
          }
          description
            "Online PPP user number.";
        }
        leaf flow-down-byte {
          type uint64;
          units Byte;
          description
            "Flow Down Byte.";
        }
        leaf flow-down-packet {
          type uint64;
          description
            "Flow Down Packet.";
        }
        leaf flow-up-byte {
          type uint64;
          units Byte;
          description
            "Flow Up Byte.";
        }
        leaf flow-up-packet {
          type uint64;
          description
            "Flow Up Packet.";
        }
        leaf ip-total-number {
          type int32 {
            range "0..2147483647";
          }
          description
            "Total IP addresses number configured in this domain.";
        }
        leaf ip-used-number {
          type int32 {
            range "0..2147483647";
          }
          description
            "Used IP addresses number.";
        }
        leaf ip-conflict-number {
          type int32 {
            range "0..2147483647";
          }
          description
            "Conflicted IP addresses number.";
        }
        leaf ip-exclude-number {
          type int32 {
            range "0..2147483647";
          }
          description
            "Excluded IP addresses number.";
        }
        leaf ip-idle-number {
          type int32 {
            range "0..2147483647";
          }
          description
            "Idle IP addresses number.";
        }
        leaf ip-used-percent {
          type string {
            length "1..64";
          }
          description
            "IP address used percent.";
        }
        leaf pppoe-user-number {
          type int32 {
            range "0..2147483647";
          }
          description
            "PPPoE user number.";
        }
        leaf authen-request-number {
          type uint32 {
            range "0..2147483647";
          }
          description
            "Domain authen requests number.";
        }
        leaf authen-accept-number {
          type uint32 {
            range "0..2147483647";
          }
          description
            "Domain authen accepts number.";
        }
        leaf authen-reject-number {
          type uint32 {
            range "0..2147483647";
          }
          description
            "Domain authen rejects number.";
        }
        leaf acct-request-number {
          type uint32 {
            range "0..2147483647";
          }
          description
            "Domain acct requests number.";
        }
        leaf acct-success-number {
          type uint32 {
            range "0..2147483647";
          }
          description
            "Domain acct success number.";
        }
        leaf acct-request-fail-number {
          type uint32 {
            range "0..2147483647";
          }
          description
            "Domain acct requests failures number.";
        }
        leaf ipv6-address-total-number {
          type int32 {
            range "0..2147483647";
          }
          description
            "The total IPv6 address number of domain.";
        }
        leaf ipv6-address-used-number {
          type int32 {
            range "0..2147483647";
          }
          description
            "The used IPv6 address number of domain.";
        }
        leaf ipv6-address-free-number {
          type int32 {
            range "0..2147483647";
          }
          description
            "The free IPv6 address number of domain.";
        }
        leaf ipv6-address-conflict-number {
          type int32 {
            range "0..2147483647";
          }
          description
            "The conflict IPv6 address number of domain.";
        }
        leaf ipv6-address-exclude-number {
          type int32 {
            range "0..2147483647";
          }
          description
            "The excluded IPv6 address number of domain.";
        }
        leaf ipv6-address-used-percent {
          type string {
            length "1..64";
          }
          description
            "The percent of used IPv6 address of domain.";
        }
        leaf ndra-prefix-total-number {
          type int32 {
            range "0..2147483647";
          }
          description
            "The total NDRA prefix number of domain.";
        }
        leaf ndra-prefix-used-number {
          type int32 {
            range "0..2147483647";
          }
          description
            "The used NDRA prefix number of domain.";
        }
        leaf ndra-prefix-free-number {
          type int32 {
            range "0..2147483647";
          }
          description
            "The free NDRA prefix number of domain.";
        }
        leaf ndra-prefix-conflict-number {
          type int32 {
            range "0..2147483647";
          }
          description
            "The conflict NDRA prefix number of domain.";
        }
        leaf ndra-prefix-exclude-number {
          type int32 {
            range "0..2147483647";
          }
          description
            "The excluded NDRA prefix number of domain.";
        }
        leaf ndra-prefix-used-percent {
          type string {
            length "1..64";
          }
          description
            "The percent of used IPv6 NDRA prefix of domain.";
        }
        leaf pd-prefix-total-number {
          type int32 {
            range "0..2147483647";
          }
          description
            "The total PD prefix number of domain.";
        }
        leaf pd-prefix-used-number {
          type int32 {
            range "0..2147483647";
          }
          description
            "The used PD prefix number of domain.";
        }
        leaf pd-prefix-free-number {
          type int32 {
            range "0..2147483647";
          }
          description
            "The free PD prefix number of domain.";
        }
        leaf pd-prefix-conflict-number {
          type int32 {
            range "0..2147483647";
          }
          description
            "The conflict PD prefix number of domain.";
        }
        leaf pd-prefix-exclude-number {
          type int32 {
            range "0..2147483647";
          }
          description
            "The excluded PD prefix number of domain.";
        }
        leaf pd-prefix-used-percent {
          type string {
            length "1..64";
          }
          description
            "The percent of used IPv6 PD prefix of domain.";
        }
        leaf ipv6-flow-down-byte {
          type uint64;
          units Byte;
          description
            "The IPv6 flow down byte in a domain.";
        }
        leaf ipv6-flow-down-packet {
          type uint64;
          description
            "The IPv6 flow down packet in a domain.";
        }
        leaf ipv6-flow-up-byte {
          type uint64;
          units Byte;
          description
            "The IPv6 flow up byte in a domain.";
        }
        leaf ipv6-flow-up-packet {
          type uint64;
          description
            "The IPv6 flow up packet in a domain.";
        }
        leaf ipv4-usage-warning {
          type bras-user-manage-warning-type;
          description
            "IPv4 address pool overflow flag.";
        }
        leaf ipv6-usage-warning {
          type bras-user-manage-warning-type;
          description
            "IPv6 address pool overflow flag.";
        }
        leaf ipv4-usage-peak {
          type int32 {
            range "0..100";
          }
          description
            "IPv4 address usage peak.";
        }
        leaf ipv4-usage-peak-time {
          type string {
            length "1..32";
          }
          description
            "Time of IPv4 address usage peak.";
        }
        leaf ipv6-usage-peak {
          type int32 {
            range "0..100";
          }
          description
            "IPv6 address usage peak.";
        }
        leaf ipv6-usage-peak-time {
          type string {
            length "1..32";
          }
          description
            "Time of IPv6 address usage peak.";
        }
        leaf nd-usage-warning {
          type bras-user-manage-warning-type;
          description
            "The ND used status.";
        }
        leaf nd-usage-peak {
          type int32 {
            range "0..100";
          }
          description
            "ND usage peak.";
        }
        leaf nd-usage-peak-time {
          type string {
            length "1..32";
          }
          description
            "Time of ND usage peak.";
        }
        leaf pd-usage-warning {
          type bras-user-manage-warning-type;
          description
            "The PD used status.";
        }
        leaf pd-usage-peak {
          type int32 {
            range "0..100";
          }
          description
            "PD usage peak.";
        }
        leaf pd-usage-peak-time {
          type string {
            length "1..32";
          }
          description
            "Time of PD usage peak.";
        }
      }
    }
    container vas-user-statistics {
      config false;
      description
        "List of the online users using the value-added service.";
      list vas-user-statistic {
        key "service-type";
        description
          "Statistics of online users using the value-added service.";
        leaf service-type {
          type enumeration {
            enum "bod" {
              value 0;
              description
                "BOD services.";
            }
            enum "daa" {
              value 1;
              description
                "DAA services.";
            }
            enum "edsg" {
              value 2;
              description
                "EDSG services.";
            }
          }
          description
            "Indicates the service type.";
        }
        leaf normal-users {
          type uint32;
          description
            "Number of other (non-RUI) users.";
        }
        leaf rui-local-users {
          type uint32;
          description
            "Number of local RUI users.";
        }
        leaf rui-remote-users {
          type uint32;
          description
            "Number of remote RUI users.";
        }
        leaf total-users {
          type uint32;
          description
            "Total number of online users.";
        }
        container detail-states {
          description
            "List of the online users using the value-added service.";
          list detail-state {
            key "user-id";
            description
              "Statistics of online users using the value-added service.";
            leaf user-id {
              type uint32;
              description
                "User index.";
            }
            leaf user-name {
              type string {
                length "1..253";
              }
              description
                "User name.";
            }
            leaf interface-name {
              type string {
                length "1..254";
              }
              description
                "Interface through which the user accesses the router.";
            }
            leaf ip-address {
              type inet:ipv4-address-no-zone;
              description
                "User IP address.";
            }
            leaf mac {
              type pub-type:mac-address;
              description
                "User MAC address.";
            }
            leaf pe-vlan-start-id {
              type uint16;
              description
                "Display the start VLANID in the outer VLAN range.";
            }
            leaf ce-vlan-start-id {
              type uint16;
              description
                "Display the start VLANID in the inner VLAN range.";
            }
            leaf ipv6-address {
              type string {
                length "1..127";
              }
              description
                "IPv6 address.";
            }
            leaf access-type {
              type string {
                length "1..29";
              }
              description
                "User access type.";
            }
          }
        }
      }
    }
    container pevlan-flow-statistics {
      config false;
      description
        "List of the PEVLAN flow.";
      list pevlan-flow-statistic {
        key "pevlan";
        description
          "Statistics of the PEVLAN flow.";
        leaf pevlan {
          type int32 {
            range "1..4094";
          }
          description
            "Outer VLAN.";
        }
        uses flow-statistics-information;
      }
    }
    container cevlan-flow-statistics {
      config false;
      description
        "List of the CEVLAN flow.";
      list cevlan-flow-statistic {
        key "cevlan";
        description
          "Statistics of the CEVLAN flow.";
        leaf cevlan {
          type int32 {
            range "1..4094";
          }
          description
            "Inner VLAN.";
        }
        uses flow-statistics-information;
      }
    }
    container web-module-statistics {
      config false;
      description
        "List of the web module.";
      list web-module-statistic {
        key "ip-address vpn-name slave-board";
        description
          "Statistics of the web module.";
        leaf ip-address {
          type inet:ip-address-no-zone;
          description
            "Display statistics about web packets exchanged between the device and a web authentication server of a specified IP address.";
        }
        leaf vpn-name {
          type string {
            length "1..31";
          }
          description
            "Name of a VPN instance.";
        }
        leaf slave-board {
          type boolean;
          description
            "Display information on the slave main control board.";
        }
        leaf challenge-request-accept-server {
          type uint32;
          description
            "Number of Challenge request packets received from the web authentication server.";
        }
        leaf challenge-request-drop-server {
          type uint32;
          description
            "Number of Challenge request packets received from the web authentication server that are discarded.";
        }
        leaf auth-request-accept-server {
          type uint32;
          description
            "Number of authentication request packets received from the web authentication server.";
        }
        leaf auth-request-drop-server {
          type uint32;
          description
            "Number of authentication request packets received from the web authentication server that are discarded.";
        }
        leaf auth-ack-affirm-accept-server {
          type uint32;
          description
            "Number of authentication success acknowledgement packets received from the web authentication server.";
        }
        leaf auth-ack-affirm-drop-server {
          type uint32;
          description
            "Number of authentication success acknowledgement packets received from the web authentication server that are discarded.";
        }
        leaf logout-request-accept-server {
          type uint32;
          description
            "Number of user logout request packets received from the web authentication server.";
        }
        leaf logout-request-drop-server {
          type uint32;
          description
            "Number of user logout request packets received from the web authentication server that are discarded.";
        }
        leaf info-request-accept-server {
          type uint32;
          description
            "Number of Information request packets received from the web authentication server.";
        }
        leaf info-request-drop-server {
          type uint32;
          description
            "Number of Information request packets received from the web authentication server that are discarded.";
        }
        leaf user-discovery-accept-server {
          type uint32;
          description
            "Number of user discovery packets received from the web authentication server.";
        }
        leaf user-discovery-drop-server {
          type uint32;
          description
            "Number of user discovery packets received from the web authentication server that are discarded.";
        }
        leaf logout-ack-accept-server {
          type uint32;
          description
            "Number of user logout acknowledgement packets received from the web authentication server.";
        }
        leaf logout-ack-drop-server {
          type uint32;
          description
            "Number of user logout acknowledgement packets received from the web authentication server that are discarded.";
        }
        leaf user-ip-change-ack-accept-server {
          type uint32;
          description
            "Number of user address change acknowledgment packets received from the web authentication server.";
        }
        leaf user-ip-change-ack-drop-server {
          type uint32;
          description
            "Number of user address change acknowledgment packets received from the web authentication server that are discarded.";
        }
        leaf status-notify-accept-server {
          type uint32;
          description
            "Number of status notification packets received from the web authentication server.";
        }
        leaf status-notify-drop-server {
          type uint32;
          description
            "Number of status notification packets received from the web authentication server that are discarded.";
        }
        leaf version-error-server {
          type uint32;
          description
            "Number of packets with incorrect version numbers received from the web authentication server.";
        }
        leaf authenticator-error-server {
          type uint32;
          description
            "Number of packets with incorrect authenticators received from the web authentication server.";
        }
        leaf drop-packet-total-server {
          type uint32;
          description
            "Total number of packets received from the web authentication server that are discarded.";
        }
        leaf challenge-request-accept-rui-peer {
          type uint32;
          units packet;
          description
            "Number of Challeng request packets received from the RUI peer.";
        }
        leaf challenge-request-drop-rui-peer {
          type uint32;
          units packet;
          description
            "Number of Challeng request packets received from the RUI peer that are discarded.";
        }
        leaf auth-request-accept-rui-peer {
          type uint32;
          units packet;
          description
            "Number of authentication request packets received from the RUI peer.";
        }
        leaf auth-request-drop-rui-peer {
          type uint32;
          units packet;
          description
            "Number of authentication request packets received from the RUI peer that are discarded.";
        }
        leaf auth-ack-affirm-accept-rui-peer {
          type uint32;
          units packet;
          description
            "Number of authentication success acknowledgement packets received from the RUI peer.";
        }
        leaf auth-ack-affirm-drop-rui-peer {
          type uint32;
          units packet;
          description
            "Number of authentication success acknowledgement packets received from the RUI peer that are discarded.";
        }
        leaf logout-request-accept-rui-peer {
          type uint32;
          units packet;
          description
            "Number of user logout request packets received from the RUI peer.";
        }
        leaf logout-request-drop-rui-peer {
          type uint32;
          units packet;
          description
            "Number of user logout request packets received from the RUI peer that are discarded.";
        }
        leaf info-request-accept-rui-peer {
          type uint32;
          units packet;
          description
            "Number of information request packets received from the RUI peer.";
        }
        leaf info-request-drop-rui-peer {
          type uint32;
          units packet;
          description
            "Number of information request packets received from the RUI peer that are discarded.";
        }
        leaf user-discovery-accept-rui-peer {
          type uint32;
          units packet;
          description
            "Number of user discovery packets received from the RUI peer.";
        }
        leaf user-discovery-drop-rui-peer {
          type uint32;
          units packet;
          description
            "Number of user discovery packets received from the RUI peer that are discarded.";
        }
        leaf logout-ack-accept-rui-peer {
          type uint32;
          units packet;
          description
            "Number of user logout acknowledgement packets received from the RUI peer.";
        }
        leaf logout-ack-drop-rui-peer {
          type uint32;
          units packet;
          description
            "Number of user logout acknowledgement packets received from the RUI peer that are discarded.";
        }
        leaf user-ip-change-ack-accept-rui-peer {
          type uint32;
          units packet;
          description
            "Number of user address change acknowledgement packets received from the RUI peer.";
        }
        leaf user-ip-change-ack-drop-rui-peer {
          type uint32;
          units packet;
          description
            "Number of user address change acknowledgement packets received from the RUI peer that are discarded.";
        }
        leaf status-notify-accept-rui-peer {
          type uint32;
          units packet;
          description
            "Number of status notification packets received from the RUI peer.";
        }
        leaf status-notify-drop-rui-peer {
          type uint32;
          units packet;
          description
            "Number of status notification packets received from the RUI peer that are dropped.";
        }
        leaf version-error-rui-peer {
          type uint32;
          units packet;
          description
            "Number of packets with incorrect version numbers received from the RUI peer.";
        }
        leaf authenticator-error-rui-peer {
          type uint32;
          units packet;
          description
            "Number of packets with incorrect authenticators received from the RUI peer.";
        }
        leaf drop-packet-total-rui-peer {
          type uint32;
          units packet;
          description
            "Total number of discarded packets that are received from the RUI peer.";
        }
        leaf drop-packets-too-fast {
          type uint32;
          units packet;
          description
            "Number of packets discarded due to rate limit.";
        }
        leaf drop-packets-cpu-limit {
          type uint32;
          units packet;
          description
            "Number of discarded packets due to CPU limit.";
        }
        leaf query-base-on-mac-address {
          type uint32;
          units packet;
          description
            "Number of packets sent to query user CIDs based on user MAC addresses.";
        }
        leaf query-base-on-ip-address {
          type uint32;
          units packet;
          description
            "Number of packets sent to query user CIDs based on user IP addresses.";
        }
        leaf query-base-on-user-name {
          type uint32;
          units packet;
          description
            "Number of packets sent to query user CIDs based on user names.";
        }
        leaf query-base-onuser-account-id {
          type uint32;
          units packet;
          description
            "Number of packets sent to query user CIDs based on user accounting IDs.";
        }
        leaf sent-challenge-ack-success {
          type uint32;
          description
            "Number of successfully sent Challenge acknowledgement packets.";
        }
        leaf sent-challenge-ack-fail {
          type uint32;
          description
            "Number of unsuccessfully sent Challenge acknowledgement packets.";
        }
        leaf sent-auth-ack-success {
          type uint32;
          description
            "Number of successfully sent authentication acknowledgement packets.";
        }
        leaf sent-auth-ack-fail {
          type uint32;
          description
            "Number of unsuccessfully sent authentication acknowledgement packets.";
        }
        leaf sent-logout-ack-success {
          type uint32;
          description
            "Number of successfully sent logout acknowledgement packets.";
        }
        leaf sent-logout-ack-fail {
          type uint32;
          description
            "Number of unsuccessfully sent logout acknowledgement packets.";
        }
        leaf sent-logout-notify-success {
          type uint32;
          description
            "Number of successfully sent forcible logout notification packets.";
        }
        leaf sent-logout-notify-fail {
          type uint32;
          description
            "Number of unsuccessfully sent forcible logout notification packets.";
        }
        leaf sent-information-ack-success {
          type uint32;
          description
            "Number of successfully sent information request acknowledgement packets.";
        }
        leaf sent-information-ack-fail {
          type uint32;
          description
            "Number of unsuccessfully sent information request acknowledgement packets.";
        }
        leaf query-in-auth-domain {
          type uint32;
          units packet;
          description
            "User statistics in the authentication domain.";
        }
        leaf query-in-preauth-domain {
          type uint32;
          units packet;
          description
            "User statistics in the pre-authentication domain.";
        }
        leaf query-for-excluded-users {
          type uint32;
          description
            "Statistics about blocked users.";
        }
        leaf query-for-offline-users {
          type uint32;
          description
            "Statistics about offline users.";
        }
        leaf sent-user-ip-change-success {
          type uint32;
          description
            "Number of successfully sent user address change notification packets.";
        }
        leaf sent-user-ip-change-fail {
          type uint32;
          description
            "Number of unsuccessfully sent user address change notification packets.";
        }
        leaf sent-status-notify-ack-success {
          type uint32;
          description
            "Number of successfully sent status notification acknowledgement packets.";
        }
        leaf sent-status-notify-ack-fail {
          type uint32;
          description
            "Number of unsuccessfully sent status notification acknowledgement packets.";
        }
      }
    }
    container web-statistics {
      config false;
      description
        "Portal packet statistics.";
      leaf begin-time {
        type string {
          length "1..23";
        }
        description
          "The time of system startup time, statistics of start time. When clear the statistics data, it will be reset. If power off, the data would not be saved.";
      }
      leaf packet-authenticator-error {
        type uint64;
        description
          "The total packet number of validate failure.";
      }
      leaf packet-access-request-error {
        type uint64;
        description
          "The total number of access request error packet.";
      }
      leaf packet-logout-request-error {
        type uint64;
        description
          "The total number of logout request error packet.";
      }
      leaf packet-inquiry-request-error {
        type uint64;
        description
          "The total number of inquiry request error packet.";
      }
      leaf packet-login-confirm-error {
        type uint64;
        description
          "The total number of login confirm error packet.";
      }
      leaf packet-access-request-recv {
        type uint64;
        description
          "The total number of received access request packet.";
      }
      leaf packet-login-request-recv {
        type uint64;
        description
          "The total number of received login request packet.";
      }
      leaf packet-logout-request-recv {
        type uint64;
        description
          "The total number of received logout request packet.";
      }
      leaf packet-inquiry-request-recv {
        type uint64;
        description
          "The total number of received inquiry request packet.";
      }
      leaf packet-login-confirm-recv {
        type uint64;
        description
          "The total number of received login confirm packet.";
      }
      leaf packet-access-ack-failure {
        type uint64;
        description
          "The total number of access ack failure packet.";
      }
      leaf packet-login-ack-failure {
        type uint64;
        description
          "The total number of login ack failure packet.";
      }
      leaf packet-logout-ack-failure {
        type uint64;
        description
          "The total number of logout ack failure packet.";
      }
      leaf packet-inquiry-ack-failure {
        type uint64;
        description
          "The total number of inquiry ack failure packet.";
      }
      leaf packet-access-ack-sent {
        type uint64;
        description
          "The total number of sending access ack packet.";
      }
      leaf packet-login-ack-sent {
        type uint64;
        description
          "The total number of sending login ack packet.";
      }
      leaf packet-logout-ack-sent {
        type uint64;
        description
          "The total number of sending logout ack packet.";
      }
      leaf packet-inquiry-ack-sent {
        type uint64;
        description
          "The total number of sending inquiry ack packet.";
      }
    }
    container interface-access-user-statistics {
      config false;
      description
        "List of the users on a specified interface.";
      list interface-access-user-statistic {
        key "interface-name user-type";
        description
          "Statistics of users on a specified interface.";
        leaf interface-name {
          type string {
            length "1..63";
          }
          description
            "The name of interface.";
        }
        leaf user-type {
          type bras-user-manage-user-type;
          description
            "User type.";
        }
        leaf user-number {
          type int32 {
            range "0..256000";
          }
          description
            "User number.";
        }
      }
    }
    container web-auth-servers {
      config false;
      description
        "List of every access user on PORTAL server.";
      list web-auth-server {
        key "server-ip-address vpn-name";
        description
          "Statistics of every access user on PORTAL server.";
        leaf server-ip-address {
          type inet:ipv4-address-no-zone;
          description
            "The IP address of PORTAL server.";
        }
        leaf vpn-name {
          type string {
            length "1..31";
          }
          description
            "The name of VPN.";
        }
        leaf server-user-number {
          type int32 {
            range "0..2147483647";
          }
          description
            "The total number of access users on PORTAL server.";
        }
      }
    }
    container slot-card-connect-statistics {
      config false;
      description
        "List of the access users on the board in a specified slot.";
      list slot-card-connect-statistic {
        key "slot-id card-id";
        description
          "Statistics of the access users on the board in a specified slot.";
        leaf slot-id {//int To string
          type string {
            length "1..32";
          }
          description
            "User Slot.";
        }
        leaf card-id {
          type int32 {
            range "0..2147483647";
          }
          description
            "User Card.";
        }
        leaf online-number {
          type int32 {
            range "0..2147483647";
          }
          description
            "Online user number.";
        }
        leaf ipv4-online-number {
          type int32 {
            range "0..2147483647";
          }
          description
            "Online IPv4 user number.";
        }
        leaf ipv6-online-number {
          type int32 {
            range "0..2147483647";
          }
          description
            "Online IPv6 user number.";
        }
        leaf dual-stack-online-number {
          type int32 {
            range "0..2147483647";
          }
          description
            "Online Dual-stack user number.";
        }
        leaf no-authentication-online-number {
          type int32 {
            range "0..2147483647";
          }
          description
            "Online no authentication user number.";
        }
        leaf ppp-authentication-number {
          type int32 {
            range "0..2147483647";
          }
          description
            "Online PPP authentication user number.";
        }
        leaf access-8021-xauth-number {
          type int32 {
            range "0..2147483647";
          }
          description
            "Online 802.1x authentication user number.";
        }
        leaf web-authentication-number {
          type int32 {
            range "0..2147483647";
          }
          description
            "Online web authentication user number.";
        }
        leaf bind-authentication-number {
          type int32 {
            range "0..2147483647";
          }
          description
            "Online bind authentication user number.";
        }
        leaf fast-authentication-number {
          type int32 {
            range "0..2147483647";
          }
          description
            "Online fast authentication user number.";
        }
        leaf wlan-authentication-number {
          type int32 {
            range "0..2147483647";
          }
          description
            "Online wlan authentication user number.";
        }
        leaf admin-authentication-number {
          type int32 {
            range "0..2147483647";
          }
          description
            "Online admin authentication user number.";
        }
        leaf tunnel-authentication-number {
          type int32 {
            range "0..2147483647";
          }
          description
            "Online tunnel authentication user number.";
        }
        leaf mip-authentication-number {
          type int32 {
            range "0..2147483647";
          }
          description
            "Online MIP authentication user number.";
        }
      }
    }
    container access-user-accounting-copy-infos {
      config false;
      description
        "List of the user access accounting copy informations.";
      list access-user-accounting-copy-info {
        key "access-index";
        description
          "Operational data of user access accounting copy.";
        leaf access-index {
          type uint32 {
            range "0..2147483647";
          }
          description
            "Access user index.";
        }
        leaf accounting-copy-group-name {
          type leafref {
            path "/bras-user-manage:bras-user-manage/bras-user-manage:accounting-copy-groups/bras-user-manage:accounting-copy-group/bras-user-manage:name";
          }
          description
            "The name of an accounting copy group.";
        }
        container access-user-mult-server-infos {
          description
            "List of the user access accounting copy multiple server informations.";
          list access-user-mult-server-info {
            key "radius-server-group-name";
            description
              "Operational data of user access accounting copy multiple server.";
            leaf radius-server-group-name {
              type leafref {
                path "/radius:radius/radius:radius-server-groups/radius:radius-server-group/radius:name";
              }
              description
                "The name of an accounting copy server.";
            }
            leaf accounting-interval {
              type uint32 {
                range "1..65535";
              }
              units min;
              description
                "The interval of an accounting copy RADIUS server group to send accounting packets.";
            }
          }
        }
      }
    }
    container access-radius-attribute-info {
      config false;
      description
        "Statistics of the access user radius attribute info.";
      container framed-routes {
        description
          "List of the framed route.";
        list framed-route {
          key "user-id route-index";
          description
            "Statistics of framed route.";
          leaf user-id {
            type uint32;
            description
              "User ID.";
          }
          leaf route-index {
            type uint32;
            description
              "Route index of a route.";
          }
          leaf prefix {
            type inet:ipv4-address-no-zone;
            description
              "Prefix of the destination address of a route.";
          }
          leaf prefix-length {
            type uint8 {
              range "1..32";
            }
            description
              "Prefix length of the destination address of a route.";
          }
          leaf next-hop {
            type inet:ipv4-address-no-zone;
            description
              "Next hop address of a route.";
          }
          leaf cost {
            type uint32;
            description
              "Cost of a route.";
          }
        }
      }
      container ipv6-framed-routes {
        description
          "List of the IPv6 framed routes.";
        list ipv6-framed-route {
          key "user-id route-index";
          description
            "Statistics of framed routes.";
          leaf user-id {
            type uint32;
            description
              "User ID.";
          }
          leaf route-index {
            type uint32;
            description
              "Route index of a route.";
          }
          leaf prefix {
            type inet:ipv6-address-no-zone;
            description
              "Prefix of the destination address of a route.";
          }
          leaf prefix-length {
            type uint8 {
              range "1..128";
            }
            description
              "Prefix length of the destination address of a route.";
          }
          leaf next-hop {
            type inet:ipv6-address-no-zone;
            description
              "Next hop address of a route.";
          }
          leaf cost {
            type uint32;
            description
              "Cost of a route.";
          }
        }
      }
    }
    container up-access-users {
      config false;
      description
        "List of access user information on the UP device.";
      list up-access-user {
        key "up-cid";
        description
          "Operational data of access user on the UP device.";
        leaf up-cid {
          type uint32;
          description
            "User ID on the UP device.";
        }
        leaf cp-cid {
          ext:support-filter "true";
          type uint32;
          description
            "User ID on the CP device.";
        }
        leaf ipv4-address {
          ext:support-filter "true";
          type inet:ipv4-address-no-zone;
          description
            "IPv4 address of the user.";
        }
        leaf ipv6-address {
          ext:support-filter "true";
          type inet:ipv6-address-no-zone;
          description
            "IPv6 address of the user.";
        }
        leaf ipv4-vpn-instance {
          ext:support-filter "true";
          type string {
            length "1..31";
          }
          description
            "IPv4 stack VPN instance of the user.";
        }
        leaf ipv6-vpn-instance {
          ext:support-filter "true";
          type string {
            length "1..31";
          }
          description
            "IPv6 stack VPN instance of the user.";
        }
        leaf mac-address {
          ext:support-filter "true";
          type pub-type:mac-address;
          description
            "MAC address of the user.";
        }
        leaf interface {
          ext:support-filter "true";
          type string {
            length "1..63";
          }
          description
            "Interface name of the user.";
        }
        leaf pevlan {
          ext:support-filter "true";
          type uint16 {
            range "1..4094";
          }
          description
            "Outer VLAN of the user.";
        }
        leaf cevlan {
          ext:support-filter "true";
          type uint16 {
            range "1..4094";
          }
          description
            "Inner VLAN of the user.";
        }
      }
    }
  }
  rpc set-cache-local-bill-backup {
    description
      "Back up bills in the cache to the CF card or bill server.";
    ext:node-ref "bras-user-manage:bras-user-manage/bras-user-manage:local-bill";
  }
  rpc set-cfcard-local-bill-backup {
    description
      "Back up bills in the CF card to a bill server.";
    ext:node-ref "bras-user-manage:bras-user-manage/bras-user-manage:local-bill";
    input {
      leaf file-name {
        type string {
          length "1..30";
        }
        description
          "Name of the file used to store CDRs on a bill server, excluding a suffix.";
      }
    }
  }
  rpc reset-cfcard-local-bill {
    description
      "Clear all the bills in the CF card.";
    ext:node-ref "bras-user-manage:bras-user-manage/bras-user-manage:local-bill";
  }
  rpc reset-access-packet-discard-statistics {
    description
      "Clears statistics about MAC-spoofing-dropped or URPF-dropped packets of access users.";
    ext:node-ref "/bras-user-manage:bras-user-manage/bras-user-manage:access-packet-discard-statistics";
    input {
      leaf discard-type {
        type enumeration {
          enum "mac-spoofing" {
            value 1;
            description
              "Clears statistics about MAC-spoofing-dropped packets of access users.";
          }
          enum "urpf" {
            value 2;
            description
              "Clears statistics about URPF-dropped packets of access users.";
          }
        }
        mandatory true;
        description
          "Discared type.";
      }
      leaf user-type {
        type enumeration {
          enum "ipv4" {
            value 1;
            description
              "Clears statistics about MAC-spoofing-dropped IPv4 packets.";
          }
          enum "ipv6" {
            value 2;
            description
              "Clears statistics about MAC-spoofing-dropped IPv6 packets.";
          }
        }
        description
          "User type.";
      }
      leaf access-type {
        type enumeration {
          enum "pppoe" {
            value 1;
            description
              "Clears statistics about URPF-dropped packets of PPPoX users.";
          }
          enum "ipoe" {
            value 2;
            description
              "Clears statistics about URPF-dropped packets of IPoX users.";
          }
        }
        description
          "Access type.";
      }
      choice based-type {
        mandatory true;
        description
          "Clears statistics about discard packets of interfaces or slot.";
        case interface {
          description
            "Interface name.";
          leaf interface {
            type leafref {
              path "/ifm:ifm/ifm:interfaces/ifm:interface/ifm:name";
            }
            description
              "Interface name.";
          }
        }
        case slot {
          description
            "Specifies a slot ID.";
          leaf slot {
            type leafref {
              path "/devm:devm/devm:lpu-boards/devm:lpu-board/devm:position";
            }
            description
              "ID of an available slot.";
          }
        }
      }
    }
  }
  rpc reset-domain-statistics {
    description
      "Clear statistics about authentication or accounting packets.";
    ext:node-ref "/bras-user-manage/domain-statistics/domain-statistic";
    input {
      leaf packet-type {
        type enumeration {
          enum "accounting" {
            value 0;
            description
              "Clears the statistics on accounting packets.";
          }
          enum "authentication" {
            value 1;
            description
              "Clears the statistics on authentication packets.";
          }
        }
        mandatory true;
        description
          "Authentication packets or accounting packets.";
      }
      leaf domain-name {
        type leafref {
          path "/aaa:aaa/aaa:domains/aaa:domain/aaa:name";
        }
        description
          "Specifies the name of a domain.";
      }
    }
  }
  rpc reset-online-fail-record-statistics {
    description
      "Resets the online fail number of DHCP users.";
    ext:node-ref "/bras-user-manage/online-fail-record-statistic";
  }
  rpc reauthorize-user-name {
    description
      "Modify the user group of an online user.";
    input {
      leaf user-name {
        type string {
          length "1..253";
        }
        mandatory true;
        description
          "Name of the user whose user group is to be replaced.";
      }
      leaf user-group-name {
        type leafref {
          path "/bras-basic-access:bras-basic-access/bras-basic-access:user-groups/bras-basic-access:user-group/bras-basic-access:name";
        }
        mandatory true;
        description
          "Name of a user group.";
      }
    }
  }
  rpc reset-ip-userlog-statistics {
    description
      "Reset userLog statics information.";
    ext:node-ref "/bras-user-manage:bras-user-manage/bras-user-manage:ip-userlog/bras-user-manage:ip-userlog-access/bras-user-manage:statistic";
    ext:node-ref "/bras-user-manage:bras-user-manage/bras-user-manage:ip-userlog/bras-user-manage:ip-userlog-access/bras-user-manage:cu-statistics";
    ext:node-ref "/bras-user-manage:bras-user-manage/bras-user-manage:ip-userlog/bras-user-manage:ip-userlog-call-status/bras-user-manage:statistic";
    ext:node-ref "/bras-user-manage:bras-user-manage/bras-user-manage:ip-userlog/bras-user-manage:ip-userlog-call-status/bras-user-manage:cu-statistics";
    input {
      leaf reset-type {
        type enumeration {
          enum "access" {
            value 1;
            description
              "Clears statistics about user access log information.";
          }
          enum "call-status" {
            value 2;
            description
              "Clears statistics about user calling status log information.";
          }
        }
        description
          "Clears statistics about user login and logout logs.";
      }
    }
  }
  
  rpc cut-access-user-by-ip-address {
    description
      "Cuts off all connections with users in a specified IP range.";
    ext:node-ref "/bras-user-manage:bras-user-manage/bras-user-manage:access-tables";
    input {
      leaf start-ip-address {
        type inet:ipv4-address-no-zone;
        mandatory true;
        description
          "Start IP address.";
      }
      leaf end-ip-address {
        type inet:ipv4-address-no-zone;
        description
          "End IP address.";
      }
      leaf vpn-name {
        type string {
          length "1..31";
        }
        description
          "Name of a specified VPN instance.";
      }
      leaf nat-ip-address {
        type empty;
        description
          "Delete the user logout based on the public IP address of the user.";
      }
    }
  }
  rpc cut-access-user-by-condition {
    description
      "Cuts off all connections with users in a specified condition.";
    ext:node-ref "/bras-user-manage:bras-user-manage/bras-user-manage:access-tables";
    input {
      choice by-condition {
        description
          "Cuts off all connections with users in a specified condition.";
        case combinable {
          description
            "Disconnects users under specified combinable conditions.";
          leaf ip-pool-name {
            type string {
              length "1..128";
            }
            description
              "IP pool name.";
          }
          leaf ipv6-pool-name {
            type leafref {
              path "/bras-ipv6-address-manage:bras-ipv6-address-manage/bras-ipv6-address-manage:ipv6-pools/bras-ipv6-address-manage:ipv6-pool/bras-ipv6-address-manage:name";
            }
            description
              "Specifies the name of an IPv6 address pool.";
          }
          leaf domain-name {
            type leafref {
              path "/aaa:aaa/aaa:domains/aaa:domain/aaa:name";
            }
            description
              "Cuts off all connections with users in a specified domain.";
          }
          leaf user-name {
            type string {
                length "1..253";
            }
            description
              "Specifies a user name, in the format of user name@domain name.";
          }
          leaf authentication-type {
            when "../user-name";
            type bras-user-manage-authentication-type-for-cut-user;
            description
              "Disconnect the user name in the specified authentication mode.";
          }
          leaf authen-method {
            type bras-user-manage-authen-method-for-cut-user;
            description
              "Cuts off the connections with users with specified authentication mode.";
          }
          leaf interface-name {
            type leafref {
              path "/ifm:ifm/ifm:interfaces/ifm:interface/ifm:name";
            }
            description
              "Cuts off all connections with users on a specified interface.";
          }
          leaf mac-type {
            when "../interface-name";
            type enumeration {
              enum "odd-mac" {
                value 0;
                description
                  "Indicates the odd MAC address.";
              }
              enum "even-mac" {
                value 1;
                description
                  "Indicates the even MAC address.";
              }
            }
            description
                "Disconnects all connections of users with different MAC addresses on a specified interface.";
          }
          leaf pevlan {
            when "../interface-name";
            type uint32 {
                range "0..4094";
            }
            description
                "PE-VLAN ID.";
          }
          leaf cevlan {
            when "../pevlan";
            type uint32 {
              range "0..4094";
            }
            description
              "CE-VLAN ID.";
          }
          choice queue-scheduler {
            description
              "Cuts off the connections with users with specified queue scheduler.";
            case qos-profile {
              description
                "Cuts off the connections with users with specified qos profile.";
              leaf qos-profile {
                type leafref {
                  path "/qos:qos/qos:queue-scheduler-template/qos:profiles/qos:profile/qos:name";
                }
                description
                  "Cuts off the connections with users with specified qos profile.";
              }
            }
            case family-profile {
              description
                "Cuts off the connections with users with specified family profile.";
              leaf family-qos-profile {
                type leafref {
                  path "/qos:qos/qos:queue-scheduler-template/qos:profiles/qos:profile/qos:name";
                }
                description
                  "Cuts off the connections with users with specified family profile.";
              }
            }
            case queue-resources {
              description
                "Cuts off the connections with users with specified queue resources.";
              leaf resource-insufficient {
                type empty;
                description
                  "Failed to allocate user queue resources.";
              }
            }  
          }
          leaf direction {
            when "../qos-profile or ../family-qos-profile or ../resource-insufficient";
            type bras-user-manage-direction-type-for-cut-user;
            description
              "Cuts off the connections with users with specified direction.";
          }
        }
        case by-mac {
          description
            "Cuts off the connections with users with specified MAC address.";
          leaf mac {
            type pub-type:mac-address;
            description
              "User MAC address.";
          }
        }
        case by-slot {
          description
            "Cuts off the connections with users with specified slot.";
          leaf slot {
            type string {
              length "1..32";
            }
            description
              "Slot number.";
          }
        }
        case by-ipv6 {
          description
            "Cuts off the connections with users with specified IPv6 address or prefix.";
          choice address-or-prefix {
            description
              "Cuts off the connections with users with specified IPv6 address or prefix.";
            case ipv6-address {
              description
                "Cuts off the connections with users with specified IPv6 address.";
              leaf ipv6-address {
                type inet:ipv6-address-no-zone;
                description
                  "IPv6 address.";
              }
            }
            case ipv6-prefix {
              description
                "Cuts off the connections with users with specified IPv6 prefix.";
              leaf ipv6-prefix {
                type inet:ipv6-prefix;
                description
                  "Specifies a prefix address and its length.";
              }
            }
            case ipv6-segment {
              description
                "Cuts off the connections with users within the specified IPv6 prefix range.";
              leaf ipv6-segment {
                type inet:ipv6-prefix;
                description
                  "Specifies a prefix address and its length.";
              }
            }
          }
          leaf vpn-name {
            type leafref {
              path "/ni:network-instance/ni:instances/ni:instance/ni:name";
            }
            must "../ipv6-address or ../ipv6-prefix or ../ipv6-segment";
            description
              "Name of a specified VPN instance.";
          }
        }
        case by-up {
          description
              "Disconnect the user with the specified vBRAS-UP ID or resource ID.";
          choice up {
            description
              "Disconnect the user with the specified vBRAS-UP ID or resource ID.";
            case up-id {
              description
                "Disconnect the user with the specified vBRAS-UP ID.";
              leaf up-id {
                type uint32 {
                  range "1024..2023 | 2048..3047 | 3072..4071 | 4096..5095";
                }
                description
                  "Disconnect the user with the specified vBRAS-UP ID.";
              }
            }
            case up-resource {
              description
                "Disconnect the user with the specified vBRAS-UP resource ID.";
              leaf up-resource {
                type uint32 {
                  range "1024..2023 | 2048..3047 | 3072..4071 | 4096..5095";
                }
                description
                  "Disconnect the user with the specified vBRAS-UP resource ID.";
              }
            }
          }
          leaf ip-pool {
            when "../up-id or ../up-resource";
            type leafref {
              path "/bras-ipv4-address-manage:bras-ipv4-address-manage/bras-ipv4-address-manage:ipv4-pools/bras-ipv4-address-manage:ipv4-pool/bras-ipv4-address-manage:name";
            }
            description
              "IP pool name.";
          }
        }
      }
    }
  }
  rpc cut-access-user-by-user-id {
    description
      "Cut the connection with a user with a specified ID or a specified user ID range.";
    ext:node-ref "/bras-user-manage:bras-user-manage/bras-user-manage:access-tables";
    input {
      leaf start-user-id {
        type uint32;
        mandatory true;
        description
          "Specifies the start index number of the access user.";
      }
      leaf end-user-id {
        type uint32;
        must "../end-user-id >= ../start-user-id";
        description
          "Specifies the end index number of the access user.";
      }
    }
  }
  rpc cut-cgn-pub-user {
    description
      "Logs out CGN public network users and switches public IP address-based access back to private IP address-based access.";
    ext:node-ref "/bras-user-manage:bras-user-manage/bras-user-manage:access-tables";
    input {
      leaf user-type {
        type enumeration {
          enum "dhcp" {
            value 0;
            description
              "Indicates DHCP CGN public network users.";
          }
          enum "exclude-dhcp" {
            value 1;
            description
              "Indicates non-DHCP CGN public network users.";
          }
          enum "all" {
            value 2;
            description
              "Indicates CGN public network users.";
          }
        }
        description
          "Indicates the type of a CGN public network user.";
      }
    }
  }
  rpc filter-access-tables {
    description
      "List of the user access statistics tables.";
    input {
      leaf up-id {
        type int32 {
          range "1024..2023 | 2048..3047 | 3072..4071 | 4096..5095";
        }
        description
          "UP ID.";
      }
      leaf slot {
        type string {
          length "1..15";
        }
        description
          "Slot Number.";
      }
      leaf interface {
        type string {
          length "1..63";
        }
        description
          "User access interface.";
      }
      leaf pevlan-start {
        type int32 {
            range "0..4094";
        }
        description
            "PE-VLAN start ID.";
      }
      leaf pevlan-end {
        type int32 {
          range "0..4094";
        }
        description
          "PE-VLAN end ID.";
      }
      leaf cevlan-start {
        type int32 {
          range "0..4094";
        }
        description
          "CE-VLAN start ID.";
      }
      leaf cevlan-end {
        type int32 {
          range "0..4094";
        }
        description
          "CE-VLAN end ID.";
      }
      leaf user-name {
        type string {
          length "1..253";
        }
        description
          "Access user name.";
      }
      leaf domain-name {
        type string {
          length "1..64";
        }
        description
          "Domain name of a user.";
      }
      leaf mac-address {
        type pub-type:mac-address {
          length "0..255";
        }
        description
          "Mac address.";
      }
      leaf ipv4-address {
        type inet:ipv4-address-no-zone;
        description
          "IP address.";
      }
      leaf ipv6-address {
        type inet:ipv6-address-no-zone;
        description
          "IPv6 address of a user.";
      }
      leaf agent-circuit-id {
        type string {
          length "1..200";
        }
        description
          "Agent-Circuit-Id information.";
      }
      leaf ip-pool-name {
        type string {
          length "1..128";
        }
        description
          "IP address pool of a user.";
      }
      leaf ipv6-pool-name {
        type string {
          length "1..32";
        }
        description
          "IPv6 address pool of a user.";
      }
      leaf radius-server-group-name {
        type string {
          length "1..32";
        }
        description
          "RADIUS server group name.";
      }
      leaf user-group-name {
        type string {
          length "1..32";
        }
        description
          "User group name.";
      }
      leaf vpnname {
        type string {
          length "1..32";
        }
        description
          "Vpn-instance.";
      }
      leaf up-backup-profile-name {
        type string {
          length "1..32";
        }
        description
          "Up backup profile name.";
      }
    }
    output {
      container access-tables {
        description
          "List of the user access statistics tables.";
        list access-table {
          key "access-index";
          description
            "Statistics of user access statistics table.";
          leaf access-index {
            type uint32;
            description
              "Access user index.";
          }
          leaf user-name {
            type string {
              length "1..253";
            }
            description
              "Access user name.";
          }
          leaf interface {
            type string {
              length "1..63";
            }
            description
              "User access interface.";
          }
          leaf pevlan {
            type int32 {
              range "0..4094";
            }
            description
              "PEVLAN ID.";
          }
          leaf cevlan {
            type int32 {
              range "0..4094";
            }
            description
              "CEVLAN ID.";
          }
          leaf mac-address {
            type pub-type:mac-address;
            description
              "Mac address.";
          }
          leaf ipv4-address {
            type inet:ipv4-address-no-zone;
            description
              "IP address.";
          }
          leaf ipv6-address {
            type inet:ipv6-address-no-zone;
            description
              "IPv6 address of a user.";
          }
          leaf access-type {
            type string {
              length "1..64";
            }
            description
              "User access type.";
          }
        }
      }
    }
  }
  rpc filter-access-online-number-by-vlan {
    description
      "Statistics of the total number of online users based on a specified VLAN.";
    input {
      leaf pevlan-start-id {
        type uint16 {
          range "0..4094";
        }
        mandatory true;
        description
          "Start outer VLAN ID for user access, 0 means query user without VLAN.";
      }
      leaf pevlan-end-id {
        type uint16 {
          range "0..4094";
        }
        must "../pevlan-start-id and (../pevlan-end-id > ../pevlan-start-id)";
        description
          "End outer VLAN ID for user access.";
      }
      leaf cevlan-start-id {
        type uint16 {
          range "0..4094";
        }
        must "../pevlan-end-id";
        description
          "Start inner VLAN ID for user access.";
      }
      leaf cevlan-end-id {
        type uint16 {
          range "0..4094";
        }
        must "../cevlan-start-id and (../cevlan-end-id > ../cevlan-start-id)";
        description
          "End inner VLAN ID for user access.";
      }
    }
    output {
      container access-online-number-by-vlans {
        description
          "List of the user online number by VLAN.";
        list access-online-number-by-vlan {
          key "pevlan cevlan interface-name";
          description
            "Operation data of user online number by VLAN.";
          leaf pevlan {
            type uint16 {
              range "0..4094";
            }
            description
              "Outer VLAN ID for user access.";
          }
          leaf cevlan {
            type uint16 {
              range "0..4094";
            }
            description
              "Inner VLAN ID for user access.";
          }
          leaf interface-name {
            type string {
              length "1..49";
            }
            description
              "Interface name for user access.";
          }
          leaf online-total-number {
            type uint32;
            description
              "Online total number.";
          }
          leaf upmng-instance {
            type string {
              length "1..15";
            }
            description
              "UPMNG instance.";
          }
        }
      }
    }
  }
  rpc up-access-user-online-total-number {
    description
      "Statistics of the total number of access user on the UP device.";
    input  {
      leaf mac-address {
        type pub-type:mac-address;
        description
          "MAC address of the user.";
      }
      leaf interface {
        type string {
          length "1..63";
        }
        description
          "Interface name of the user.";
      }
      leaf pevlan {
        type uint16 {
          range "1..4094";
        }
        description
          "Outer VLAN of the user.";
      }
      leaf cevlan {
        type uint16 {
          range "1..4094";
        }
        description
          "Inner VLAN of the user.";
      }
    }
    output  {
      uses online-user-number;
    }
  }
  rpc reset-max-online-user {
    description
      "Reset system max online users.";
    ext:node-ref "/bras-user-manage:bras-user-manage/bras-user-manage:domain-max-online-user-statistics/bras-user-manage:domain-max-online-user-statistic";
    ext:node-ref "/bras-user-manage:bras-user-manage/bras-user-manage:max-online-user-statistic";
    input {
      choice reset-type {
        mandatory true;
        description
          "Type of reset current system max online users.";
        case by-all {
          description
            "Reset current system max online users.";
          leaf all {
            type empty;
            description
              "Reset current system max online users.";
          }
        }
        case by-domain {
          description
            "Reset max online users by domain.";
          choice name-or-all {
            description
              "Type of reset max online users by domain.";
            case by-name {
              description
                "Reset max online users by domain name.";
              leaf domain-name {
                type leafref {
                  path "/aaa:aaa/aaa:domains/aaa:domain/aaa:name";
                }
                description
                  "Domain name.";
              }
            }
            case all-domain {
              description
                "Reset max online users of all domain.";
              leaf all-domain {
                type boolean;
                description
                  "Reset max online users of all domain.";
              }
            }
          }
        }
        case by-slot {
          description
            "Reset max online users by slot.";
          leaf slot {
            type string {
              length "1..16";
            }
            description
              "Slot id.";
          }
        }
        case by-up {
          description
            "Reset max online users by up.";
          leaf up-id {
            type uint32 {
              range "1024..2023 | 2048..3047 | 3072..4071 | 4096..5095";
            }
            description
              "UP ID.";
          }
        }
      }
    }
  }
  rpc update-qoe-accounting {
    description
      "Update the QoE accounting carbon-copy configuration of users.";
  }
  rpc update-qos-profile {
    description
      "Update the QoS profile of a user.";
    ext:node-ref "/bras-user-manage/access-tables/access-table";
    input {
      leaf user-id {
        type uint32;
        mandatory true;
        description
          "ID of a user.";
      }
      leaf profile-name {
        type leafref {
          path "/qos:qos/qos:queue-scheduler-template/qos:profiles/qos:profile/qos:name";
        }
        mandatory true;
        description
          "Name of a QoS profile.";
      }
      leaf direction {
        type enumeration {
          enum "inbound" {
            value 1;
            description
              "Inbound direction.";
          }
          enum "outbound" {
            value 2;
            description
              "Outbound direction.";
          }
        }
        mandatory true;
        description
          "Specified tunnel direction.";
      }
    }
  }
  augment "/ifm:ifm/ifm:interfaces/ifm:interface/bras-basic-access:bras" {
    description
      "Bras interface.";
    container bras-user-manage {
      description
        "Configure interface.";
      container port-access-limit {
        when "(../../../ifm:type='GigabitEthernet' or
              ../../../ifm:type='10GE' or
              ../../../ifm:type='XGigabitEthernet' or
              ../../../ifm:type='100GE' or
              ../../../ifm:type='50GE' or
              ../../../ifm:type='50|100GE' or
              ../../../ifm:type='FlexE' or
              ../../../ifm:type='25GE' or
              ../../../ifm:type='Eth-Trunk' or
              ../../../ifm:type='Virtual-Ethernet' or
              ../../../ifm:type='400GE')";
        description
          "Configure the number of access users on a physical port.";
        leaf number {
          type uint32 {
            range "0..65536";
          }
          must "../../../../ifm:class!='sub-interface'";
          must "not((../../../../ifm:name)=(/ifm:ifm/ifm:interfaces/ifm:interface/ifm-trunk:trunk/ifm-trunk:members/ifm-trunk:member/ifm-trunk:name))";
          must "not(../../../../ethernet:ethernet/ethernet:main-interface/ethernet:l2-attribute)";
          description
            "Specifies the maximum number of access users on the physical port.";
        }
      }
      container vpn-flow-statistics {
        config false;
        description
          "List of the flow statistics based on interface and instance.";
        list vpn-flow-statistic {
          key "vpn-name";
          description
            "Statistics of flow based on interface and vpn instance.";
          leaf vpn-name {
            type leafref {
              path "/ni:network-instance/ni:instances/ni:instance/ni:name";
            }
            description
              "Vpn instance name.";
          }
          leaf online-user-number {
            type uint32;
            description
              "Online user number.";
          }
          uses flow-statistics-information;
        }
      }
    }
  }
  augment "/ifm:ifm/ifm:interfaces/ifm:interface/bras-basic-access:bas/bras-basic-access:access-type/bras-basic-access:layer2-subscriber/bras-basic-access:layer2-subscriber" {
    description
      "Bras user manage in bas layer2-subscriber.";
    uses bras-user-manage:bas-view-group;
    uses default-password-template;
    uses block-interface;
    uses default-user-name-template;
    container default-user-name {
      description
       "Configure a default user name.";
      leaf user-name {
        type string {
          length "1..253";
          pattern "[^\"'*?]{1,253}";
        }
        description
          "Specifies a user name.";
      }
    }
    container permit-or-deny-access {
      description
        "Configure a domain or a domain list whose users are denied or allowed on a BAS interface.";
      choice permit-or-deny {
        description
          "Configure a domain or a domain list whose users are denied or allowed on a BAS interface.";
        case deny-domain {
          description
            "Configure a domain is configured for the BAS interface to be denied access.";
          leaf-list deny-domain {
            type leafref {
              path "/aaa:aaa/aaa:domains/aaa:domain/aaa:name";
            }
            max-elements 16;
            description
              "Configure a domain is configured for the BAS interface to be denied access.";
          }
        }
        case permit-domain {
          description
            "Configure a domain is configured for the BAS interface to be permitted access.";
          leaf-list permit-domain {
            type leafref {
              path "/aaa:aaa/aaa:domains/aaa:domain/aaa:name";
            }
            max-elements 16;
            description
              "Configure a domain is configured for the BAS interface to be permitted access.";
          }
        }
        case deny-domain-group {
          description
            "A list of domains is configured for the BAS interface to be denied access.";
          container deny-domain-group {
            description
                "Configure a list of domains that are denied on a BAS interface.";
            leaf deny-domain-list {
              type leafref {
                path "/bras-user-manage:bras-user-manage/bras-user-manage:domain-lists/bras-user-manage:domain-list/bras-user-manage:name";
              }
              description
                "A list of domains is configured for the BAS interface to be denied access.";
            }
          }
        }
        case permit-domain-group {
          description
            "A list of domains that are allowed to access on the BAS interface and deny access to other domains.";
          container permit-domain-group {
            description
              "Configure a list of domains that are allowed on a BAS interface.";
            leaf permit-domain-list {
              type leafref {
                path "/bras-user-manage:bras-user-manage/bras-user-manage:domain-lists/bras-user-manage:domain-list/bras-user-manage:name";
              }
              description
                "A list of domains that are allowed to access on the BAS interface and deny access to other domains.";
            }
          }
        }
      }
    }
  }
  augment "/ifm:ifm/ifm:interfaces/ifm:interface/bras-basic-access:bas/bras-basic-access:access-type/bras-basic-access:layer3-subscriber/bras-basic-access:layer3-subscriber" {
    description
      "Bras user manage in bas layer3-subscriber.";
    uses bras-user-manage:bas-view-group;
    uses default-user-name-template;
    uses default-password-template;
  }
  augment "/ifm:ifm/ifm:interfaces/ifm:interface/bras-basic-access:bas/bras-basic-access:access-type/bras-basic-access:layer2-leaseline/bras-basic-access:layer2-leaseline" {
    description
      "Bras user manage in bas layer2-leaseline.";
    uses bras-user-manage:bas-view-group;
    uses default-user-name-template;
    uses default-password-template;
  }
  augment "/ifm:ifm/ifm:interfaces/ifm:interface/bras-basic-access:bas/bras-basic-access:access-type/bras-basic-access:layer3-leaseline/bras-basic-access:layer3-leaseline" {
    description
      "Bras user manage in bas layer3-leaseline.";
    uses default-user-name-template;
  }
  augment "/ifm:ifm/ifm:interfaces/ifm:interface/bras-basic-access:bas/bras-basic-access:access-type/bras-basic-access:l2vpn-leaseline/bras-basic-access:l2vpn-leaseline" {
    description
      "Bras user manage in bas l2vpn-leaseline.";
    uses bras-user-manage:bas-view-group;
    uses default-password-template;
  }
  augment "/aaa:aaa/aaa:accounting-schemes/aaa:accounting-scheme" {
    description
      "Bras user manage in accounting scheme.";
    container bras-user-manage {
      description
        "Configure a accounting scheme.";
      container real-time-accounting-policy {
        description
          "Configure an interval for real-time accounting and the conditions for sending real-time accounting packets and hashes real-time accounting packets and send the interim accounting packet immediately after receiving the accounting start response.";
        leaf accounting-interval {
          type uint32 {
            range "0..65535";
          }
          default "0";
          description
            "Specifies the real-time accounting interval.";
        }
        leaf accounting-unit {
          type bras-user-manage-acct-unit;
          default "minute";
          description
            "Specifies the unit of accounting interval.";
        }
        leaf traffic  {
          type boolean;
          default "false";
          description
            "Enable/disable interim accounting packet when increment of the user traffic is not zero.";
        }
        leaf hash {
          type boolean;
          default "false";
          description
            "Enable/disable the real-time accounting packets are hashed.";
        }
        leaf accounting-send-update {
          type boolean;
          default "false";
          description
            "Enable/disable the router to send the interim accounting packet immediately after receiving the accounting start response.";
        }
      }
      container accounting-fail-policy {
        description
          "Configure a policy for real-time accounting failures or an accounting start failure.";
        leaf max-times {
          type uint8 {
            range "1..255";
          }
          default "3";
          description
            "Specifies the maximum number of real-time accounting failures.";
        }
        leaf interim-fail-policy {
          type enumeration {
            enum "online" {
              value 1;
              description
                "Users keep online after accounting fail.";
            }
            enum "offline" {
              value 2;
              description
                "Users cannot go online after accounting fail.";
            }
          }
          default "online";
          description
            "Configures a policy for real-time accounting failures.";
        }
        leaf start-fail-policy {
          type enumeration {
            enum "online" {
              value 1;
              description
                "Users keep online after accounting fail.";
            }
            enum "offline" {
              value 2;
              description
                "Users cannot go online after accounting fail.";
            }
          }
          default "offline";
          description
            "Configures a policy for an accounting start failure.";
        }
        leaf keep-accounting {
          when "../start-fail-policy='online'";
          type boolean;
          default "false";
          description
            "Enable/disable a device stays in the accounting state and does not immediately send accounting stop packets.";
        }
      }
    }
  }
  augment "/aaa:aaa/aaa:authentication-schemes/aaa:authentication-scheme" {
    description
      "Bras user manage in authentication scheme.";
    container bras-user-manage {
      description
        "Configure authentication scheme.";
      container authentication-fail-policy {
        must "(authen-fail-remain-domain and (user-authen-fail-policy='online') ) or ((not(authen-fail-remain-domain) and (user-authen-fail-policy='offline') ))";
        description
          "Configure a policy to be adopted after user authentication fails.";
        leaf user-authen-fail-policy {
          type enumeration {
            enum "offline" {
              value 0;
              description
                "Forces the users failing authentication to go offline.";
            }
            enum "online" {
              value 1;
              description
                "Allows users failing authentication to remain online.";
            }
          }
          default "offline";
          description
            "Forces the users failing authentication to go offline or allows users failing authentication to remain online.";
        }
        leaf authen-fail-remain-domain {
          type leafref {
            path "/aaa:aaa/aaa:domains/aaa:domain/aaa:name";
          }
          description
            "Specifies a domain that is used for controlling the access right of a user who fails authentication but remains online.";
        }
      }
      container authentication-redirect-domain-policy {
        must "(radius-no-response-domain and (radius-no-response-policy='online') ) or ((not(radius-no-response-domain) and (radius-no-response-policy='offline') ))";
        description
          "Configure redirect domain policy.";
        leaf quota-out-redirect-enable {
          type boolean;
          default "false";
          description
            "Enable/disable the function of redirecting a user to a specified domain when the quota of the user equal to zero.";
        }
        leaf redirect-domain {
          type leafref {
            path "/aaa:aaa/aaa:domains/aaa:domain/aaa:name";
          }
          description
            "Configures a redirection domain when the user quota is used up.";
        }
        leaf radius-no-response-policy {
          type enumeration {
            enum "online" {
              value 1;
              description
                "Indicates that users stay online.";
            }
            enum "offline" {
              value 2;
              description
                "Indicates that users go offline.";
            }
          }
          default "offline";
          description
            "Configures a policy when users' RADIUS authentication packets are not responded.";
        }
        leaf radius-no-response-domain {
          type leafref {
            path "/aaa:aaa/aaa:domains/aaa:domain/aaa:name";
          }
          description
            "Indicates the domain in which users stay online if their RADIUS authentication packets are not responded.";
        }
      }
    }
  }
  augment "/aaa:aaa/aaa:domains/aaa:domain/bras-basic-access:bas" {
    description
      "Bras user manage in domain.";
    container bras-user-manage {
      description
        "Configure the bras user manage in domain.";
      container flow-statistic {
        description
          "Configure the system to collect the statistics about the volume of the upstream or downstream traffic of a user in a domain.";
        leaf user-up-flow-statistics {
          type boolean;
          default "true";
          description
            "Enable/disable the statistics about the volume of the upstream traffic of a user in a domain.";
        }
        leaf user-down-flow-statistics {
          type boolean;
          default "true";
          description
            "Enable/disable the statistics about the volume of the downstream traffic of a user in a domain.";
        }
      }
      container flow-bill {
        description
          "Configure the system to collect the statistics about the total traffic volume of a domain.";
        leaf enable {
          type boolean;
          default "false";
          description
            "Enable/disable the system to collect the statistics about the total traffic volume of a domain.";
        }
      }
      container access-trigger-loose {
        description
          "Configure online in loose mode after the system restarts due to an exception reduces client restarts.";
        leaf infinite-lease {
          type boolean;
          default "false";
          description
            "Enable/disable infinite of lease.";
        }
        leaf loose-time {
          when "../all-time='false'";
          type uint16 {
            range "0..1440";
          }
          units min;
          default "0";
          description
            "Period during which users can get online in loose mode after the system restarts. 0 indicates that users cannot get online in loose mode after the system restarts.";
        }
        leaf all-time {
          type boolean;
          default "false";
          description
            "Enable/disable loose mode for getting online after the system restarts.";
        }
      }
      container cpe-ip {
        description
          "Configure an IP address of the CPE in the domain.";
        leaf ip-address {
          type inet:ipv4-address-no-zone;
          description
            "Configure an IP address for the CPE in the domain.";
        }
      }
      container trunk-downstream-load-balance {
        description
          "Configure load balancing of downstream Eth-Trunk traffic.";
        leaf enable {
          type boolean;
          default "false";
          description
            "Enable/disable load balancing of downstream Eth-Trunk traffic.";
        }
      }
      container accounting-copy-group {
        description
          "Configure an accounting copy group in the domain.";
        leaf name {
          type leafref {
            path "/bras-user-manage:bras-user-manage/bras-user-manage:accounting-copy-groups/bras-user-manage:accounting-copy-group/bras-user-manage:name";
          }
          description
            "Configure the name of an accounting copy group.";
        }
      }
      container authen-fail-domain {
        description
          "Configure a domain that is used for controlling the access right of a user who fails authentication but remains online.";
        leaf name {
          type leafref {
            path "/aaa:aaa/aaa:domains/aaa:domain/aaa:name";
          }
          description
            "Specifies a domain that is used for controlling the access right of a user who fails authentication but remains online.";
        }
      }
      container qoe-accounting {
        description
          "Configure a QoE accounting copy server.";
        leaf radius-server-group-name {
          type leafref {
            path "/radius:radius/radius:radius-server-groups/radius:radius-server-group/radius:name";
          }
          description
            "Configure a QoE accounting copy server.";
        }
        leaf interval {
          type uint32 {
            range "30..1440";
          }
          units min;
          description
            "Configure a real-time accounting interval for the QoE.";
        }
      }
    }
  }

  augment "/devm:devm/devm:lpu-boards/devm:lpu-board/bras-basic-access:bras" {
    description
      "Bras user manage in slot.";
    container block {
      description
        "Configure the board is blocked.";
      leaf enable {
        type boolean;
        default "false";
        description
          "Enable/disable the status to be blocked.";
      }
    }
  }

  augment "/devm-vnf:devm-vnf/devm-vnf:vnf-boards/devm-vnf:vnf-board/bras-basic-access:bras" {
    description
      "Bras user manage in slot.";
    container ip-unr-host-route {
      description
        "Configure the route flag of the slot.";
      leaf tag {
        type uint32 {
          range "0..4294967295";
        }
        default "0";
        description
          "Tag value of slot.";
      }
    }
  }
  augment "/bras-cu-controller:bras-cu-controller/bras-cu-controller:resource-ups/bras-cu-controller:resource-up/bras-cu-controller:remote-up-boards/bras-cu-controller:remote-up-board/bras-basic-access:bras" {
    description
      "Configure bras user manage to the up board.";
    container ip-unr-host-route {
      description
        "Configure the route flag of the up board.";
      leaf tag {
        type uint32 {
          range "0..4294967295";
        }
        default "0";
        description
          "The route tag value of the up board.";
      }
    }
  }

  augment "/ni:network-instance/ni:instances/ni:instance/l3vpn:afs/l3vpn:af/bras-ipv4-address-manage:bas" {
    description
      "Configure the bras under vpn-instance.";
    container bras-user-manage {
      description
        "Configure user manage under vpn-instance.";
      container urpf {
        when "../../../l3vpn:type='ipv4-unicast' and ../../../../../ni:name!='_public_'";
        presence "IP URPF";
        description
          "Configure URPF with the vpn instance.";
        leaf enable {
          type bras-user-manage-urpf-enable-type;
          mandatory true;
          description
            "Enable/disable IP URPF.";
        }
        leaf strict-mode {
          when "../enable='enable'";
          type bras-user-manage-urpf-check-type;
          mandatory true;
          description
            "Indicates URPF check mode.";
        }
        leaf subnet-check {
          when "../enable='enable'";
          type boolean;
          default "false";
          description
            "Enable/disable IP URPF for subnet.";
        }
      }
      container ipv6-urpf {
        when "../../../l3vpn:type='ipv6-unicast' and ../../../../../ni:name!='_public_'";
        presence "IPv6 URPF";
        description
          "Configure IPv6 URPF with the vpn instance.";
        leaf enable {
          type bras-user-manage-urpf-enable-type;
          mandatory true;
          description
            "Enable/disable IPv6 URPF.";
        }
        leaf strict-mode {
          when "../enable='enable'";
          type bras-user-manage-urpf-check-type;
          mandatory true;
          description
            "Indicates IPv6 URPF check mode.";
        }
        leaf subnet-check {
          when "../enable='enable'";
          type boolean;
          default "false";
          description
            "Enable/disable IPv6 URPF for subnet.";
        }
      }
    }
  }
}
