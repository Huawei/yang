/*
Copyright (C) 2021 Huawei Technologies Co., Ltd. All rights reserved.
*/
module huawei-bras-cu-agent-deviations-NE8000M8M14 {
  namespace "urn:huawei:yang:huawei-bras-cu-agent-deviations-NE8000M8M14";
  prefix bras-cu-agent-devs-NE8000M8M14;

  import huawei-bras-cu-agent {
    prefix bras-cu-agent;
  }

  import huawei-ifm {
    prefix ifm;
  }

  import huawei-rbs {
    prefix rbs;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-cu-agent module.";

  revision 2021-05-07 {
    description
      "Initial revision.";
    reference
      "Huawei private.";
  }

  deviation "/bras-cu-agent:bras-cu-agent/bras-cu-agent:cu-agent/bras-cu-agent:link-bfd-sessions" {
    deviate not-supported;
  }
  deviation "/bras-cu-agent:bras-cu-agent/bras-cu-agent:cu-agent/bras-cu-agent:cusp-bfd-groups" {
    deviate not-supported;
  }
  deviation "/ifm:ifm/ifm:interfaces/ifm:interface/bras-cu-agent:cu-agent/bras-cu-agent:cu-multicast-rbp/bras-cu-agent:name" {
    deviate replace {
      type leafref {
        path "/rbs:rbs/rbs:profiles/rbs:profile/rbs:name";
      }
    }
  }

}
