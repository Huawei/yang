/*
Copyright (C) 2019-2021 Huawei Technologies Co., Ltd. All rights reserved.
*/
module huawei-ifm-deviations-NE8000M8M14 {
  namespace "urn:huawei:yang:huawei-ifm-deviations-NE8000M8M14";
  prefix ifm-devs-NE8000M8M14;

  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2021-05-07 {
    description
      "The deviations of the huawei-ifm module were modified.";
    reference "Huawei private.";
  }
  revision 2019-05-06 {
    description
      "Init revision.";
    reference "Huawei private.";
  }

  deviation "/ifm:ifm/ifm:global/ifm:sub-interface-link-trap-enable" {
    deviate not-supported;
  }
  deviation "/ifm:ifm/ifm:interfaces/ifm:interface/ifm:network-layer-status" {
    deviate not-supported;
  }
  deviation "/ifm:ifm/ifm:interfaces/ifm:interface/ifm:protocol-up-delay-time" {
    deviate not-supported;
  }
  deviation "/ifm:ifm/ifm:interfaces/ifm:interface/ifm:dynamic/ifm:sub-if-counts" {
    deviate not-supported;
  }
  deviation "/ifm:ifm/ifm:interfaces/ifm:interface/ifm:dynamic/ifm:license-active-status" {
    deviate not-supported;
  }
  deviation "/ifm:ifm/ifm:interfaces/ifm:interface/ifm:virtual-position" {
    deviate not-supported;
  }
  deviation "/ifm:ifm/ifm:interfaces/ifm:interface/ifm:mode-flexe" {
    deviate not-supported;
  }
  deviation "/ifm:reset-if-counters-by-type/ifm:input/ifm:if-type" {
    deviate add {
      must "../ifm:if-type='Ethernet' or ../ifm:if-type ='GigabitEthernet' or ../ifm:if-type='Eth-Trunk' or ../ifm:if-type='Ip-Trunk' or ../ifm:if-type='Pos' or ../ifm:if-type='Tunnel' or ../ifm:if-type='NULL' or ../ifm:if-type='LoopBack' or ../ifm:if-type='Vlanif' or ../ifm:if-type='100GE' or ../ifm:if-type='40GE' or ../ifm:if-type='400GE' or ../ifm:if-type='25GE' or ../ifm:if-type='MTunnel' or ../ifm:if-type='Cpos' or ../ifm:if-type='E1' or ../ifm:if-type='Serial' or ../ifm:if-type='Mp-group' or ../ifm:if-type='Virtual-Ethernet' or ../ifm:if-type='Ima-group' or ../ifm:if-type='Atm-Bundle' or ../ifm:if-type='Lmpif' or ../ifm:if-type='T1' or ../ifm:if-type='T3' or ../ifm:if-type='Global-VE' or ../ifm:if-type='Vbdif' or ../ifm:if-type='E3' or ../ifm:if-type='Pos-Trunk' or ../ifm:if-type='Trunk-Serial' or ../ifm:if-type='Global-Ima-Group' or ../ifm:if-type='Nve' or ../ifm:if-type='Virtual-Template' or ../ifm:if-type='ATM' or ../ifm:if-type='XGigabitEthernet' or ../ifm:if-type='FlexE' or ../ifm:if-type='50|100GE' or ../ifm:if-type='50GE' or ../ifm:if-type='PW-VE' or ../ifm:if-type='Virtual-Serial' or ../ifm:if-type='HP-GE'";
    }
  }
  deviation "/ifm:reset-if-mib-counters-by-type/ifm:input/ifm:if-type" {
    deviate add {
      must "../ifm:if-type='Ethernet' or ../ifm:if-type ='GigabitEthernet' or ../ifm:if-type='Eth-Trunk' or ../ifm:if-type='Ip-Trunk' or ../ifm:if-type='Pos' or ../ifm:if-type='Tunnel' or ../ifm:if-type='NULL' or ../ifm:if-type='LoopBack' or ../ifm:if-type='Vlanif' or ../ifm:if-type='100GE' or ../ifm:if-type='40GE' or ../ifm:if-type='400GE' or ../ifm:if-type='25GE' or ../ifm:if-type='MTunnel' or ../ifm:if-type='Cpos' or ../ifm:if-type='E1' or ../ifm:if-type='Serial' or ../ifm:if-type='Mp-group' or ../ifm:if-type='Virtual-Ethernet' or ../ifm:if-type='Ima-group' or ../ifm:if-type='Atm-Bundle' or ../ifm:if-type='Lmpif' or ../ifm:if-type='T1' or ../ifm:if-type='T3' or ../ifm:if-type='Global-VE' or ../ifm:if-type='Vbdif' or ../ifm:if-type='E3' or ../ifm:if-type='Pos-Trunk' or ../ifm:if-type='Trunk-Serial' or ../ifm:if-type='Global-Ima-Group' or ../ifm:if-type='Nve' or ../ifm:if-type='Virtual-Template' or ../ifm:if-type='ATM' or ../ifm:if-type='XGigabitEthernet' or ../ifm:if-type='FlexE' or ../ifm:if-type='50|100GE' or ../ifm:if-type='50GE' or ../ifm:if-type='PW-VE' or ../ifm:if-type='Virtual-Serial' or ../ifm:if-type='HP-GE'";
    }
  }
  deviation "/ifm:ifm/ifm:interfaces/ifm:interface/ifm:trap-threshold/ifm:input-rising-rate" {
    deviate replace {
      default "90";
    }
  }
  deviation "/ifm:ifm/ifm:interfaces/ifm:interface/ifm:trap-threshold/ifm:input-resume-rate" {
    deviate replace {
      default "80";
    }
  }
  deviation "/ifm:ifm/ifm:interfaces/ifm:interface/ifm:trap-threshold/ifm:output-rising-rate" {
    deviate replace {
      default "90";
    }
  }
  deviation "/ifm:ifm/ifm:interfaces/ifm:interface/ifm:trap-threshold/ifm:output-resume-rate" {
    deviate replace {
      default "80";
    }
  }
}
