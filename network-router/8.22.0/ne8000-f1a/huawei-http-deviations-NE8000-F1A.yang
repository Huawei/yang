/*
Copyright (C) 2021 Huawei Technologies Co., Ltd. All rights reserved.
*/
module huawei-http-deviations-NE8000-F1A {
  namespace "urn:huawei:yang:huawei-http-deviations-NE8000-F1A";
  prefix http-devs-NE8000-F1A;

  import huawei-http {
    prefix http;
  }
  import huawei-pub-type {
    prefix pub-type;
  }

  organization
    "Huawei Technologies Co., Ltd.";
  contact
    "Huawei Industrial Base
     Bantian, Longgang
     Shenzhen 518129
     People's Republic of China
     Website: http://www.huawei.com
     Email: support@huawei.com";
  description
    "This module defines deviation statements for huawei-http module.";

  revision 2021-05-07 {
    description
      "Initial revision.";
    reference "Huawei private.";
  }

  deviation "/http:http/http:servers" {
    deviate not-supported;
  }
  deviation "/http:http/http:server-source" {
    deviate not-supported;
  }
  deviation "/http:httpc-transfer-file/http:input/http:password" {
    deviate replace {
      type pub-type:password-extend {
        length "1..127";
      }
    }
  }
}
