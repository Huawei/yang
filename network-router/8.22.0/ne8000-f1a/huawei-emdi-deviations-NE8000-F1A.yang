/*
Copyright (C) 2019 Huawei Technologies Co., Ltd. All rights reserved.
*/
module huawei-emdi-deviations-NE8000-F1A {
  namespace "urn:huawei:yang:huawei-emdi-deviations-NE8000-F1A";
  prefix emdi-devs-NE8000-F1A;

  import huawei-emdi {
    prefix emdi;
  }

  import huawei-vlan {
    prefix vlan;
  }

  organization
    "Huawei Technologies Co., Ltd.";

  contact
    "Huawei Industrial Base
     Bantian, Longgang
     Shenzhen 518129
     People's Republic of China
     Website: http://www.huawei.com
     Email: support@huawei.com";

  description
    "This module defines deviation statements for huawei-emdi module.";

  revision 2019-11-06 {
    description
      "Initial revision.";
    reference
      "Huawei private.";
  }

  deviation "/emdi:emdi/emdi:emdi-enable/emdi:emdi-lpu-groups/emdi:emdi-lpu-group/emdi:bind-lpu/emdi:bind-slots" {
    deviate not-supported;
  }
  deviation "/emdi:emdi/emdi:emdi-enable/emdi:emdi-channel-groups/emdi:emdi-channel-group/emdi:channel-type/emdi:emdi-channel/emdi:emdi-channels/emdi:emdi-channel/emdi:channel-group-parameters/emdi:vlan-id/emdi:vlan-id" {
    deviate replace {
      type leafref {
        path "/vlan:vlan/vlan:vlans/vlan:vlan/vlan:id";
      }
    }
  }

}
