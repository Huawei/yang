/*
Copyright (C) 2021 Huawei Technologies Co., Ltd. All rights reserved.
*/
module huawei-grpc-deviations-NE8000-F1A {
  namespace "urn:huawei:yang:huawei-grpc-deviations-NE8000-F1A";
  prefix hw-grpc-devs-NE8000-F1A;

  import huawei-grpc {
    prefix hw-grpc;
  }

  organization
    "Huawei Technologies Co., Ltd.";
  contact
    "Huawei Industrial Base
     Bantian, Longgang
     Shenzhen 518129
     People's Republic of China
     Website: http://www.huawei.com
     Email: support@huawei.com";
  description
    "This module defines deviation statements for huawei-grpc module.";

  revision 2021-05-07 {
    description
      "Initial revision.";
    reference "Huawei private.";
  }

  deviation "/hw-grpc:grpc/hw-grpc:client/hw-grpc:destination-groups" {
    deviate not-supported;
  }
}
