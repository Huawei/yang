/*
Copyright (C) 2021 Huawei Technologies Co., Ltd. All rights reserved.
*/
module huawei-cli-deviations-NE8000-F1A {
  namespace "urn:huawei:yang:huawei-cli-deviations-NE8000-F1A";
  prefix cli-devs-NE8000-F1A;

  import huawei-cli {
    prefix cli;
  }

  organization
    "Huawei Technologies Co., Ltd.";
  contact
    "Huawei Industrial Base
     Bantian, Longgang
     Shenzhen 518129
     People's Republic of China
     Website: http://www.huawei.com
     Email: support@huawei.com";
  description
    "This module defines deviation statements for huawei-cli module.";

  revision 2021-05-07 {
    description
      "Initial revision.";
    reference "Huawei private.";
  }

  deviation "/cli:cli/cli:query-diagnose-information-generate-process" {
    deviate not-supported;
  }
  deviation "/cli:generate-diagnose-information" {
    deviate not-supported;
  }
  deviation "/cli:execute-command" {
    deviate not-supported;
  }
}
