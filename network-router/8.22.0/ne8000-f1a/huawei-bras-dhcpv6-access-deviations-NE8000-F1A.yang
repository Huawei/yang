/*
Copyright (C) 2021 Huawei Technologies Co., Ltd. All rights reserved.
*/
module huawei-bras-dhcpv6-access-deviations-NE8000-F1A {
  namespace "urn:huawei:yang:huawei-bras-dhcpv6-access-deviations-NE8000-F1A";
  prefix bras-dhcpv6-access-devs-NE8000-F1A;

  import huawei-bras-dhcpv6-access {
    prefix bras-dhcpv6-access;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-dhcpv6-access module.";

  revision 2021-05-07 {
    description
      "Initial revision.";
    reference
      "Huawei private.";
  }

  deviation "/bras-dhcpv6-access:bras-dhcpv6-access/bras-dhcpv6-access:cp-upgrades" {
    deviate not-supported;
  }
  deviation "/devm:devm/devm:lpu-boards/devm:lpu-board/bras-dhcpv6-access:dhcpv6-access" {
    deviate not-supported;
  }

}
