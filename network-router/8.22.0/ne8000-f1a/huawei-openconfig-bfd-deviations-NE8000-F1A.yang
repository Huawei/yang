/*
Copyright (C) 2021 Huawei Technologies Co., Ltd. All rights reserved.
*/
module huawei-openconfig-bfd-deviations-NE8000-F1A {
  namespace "urn:huawei:yang:huawei-openconfig-bfd-deviations-NE8000-F1A";
  prefix oc-bfd-devs-NE8000-F1A;

  import openconfig-bfd {
    prefix oc-bfd;
  }

  organization
    "Huawei Technologies Co., Ltd.";
  contact
    "Huawei Industrial Base
     Bantian, Longgang
     Shenzhen 518129
     People's Republic of China
     Website: http://www.huawei.com
     Email: support@huawei.com";
  description
    "This module defines deviation statements for openconfig-bfd module.";

  revision 2021-05-07 {
    description
      "Initial revision.";
    reference "Huawei private.";
  }

  deviation "/oc-bfd:bfd" {
    deviate not-supported;
  }
}
