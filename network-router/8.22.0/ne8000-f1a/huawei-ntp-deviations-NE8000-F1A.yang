/*
Copyright (C) 2021 Huawei Technologies Co., Ltd. All rights reserved.
*/
module huawei-ntp-deviations-NE8000-F1A {
  namespace "urn:huawei:yang:huawei-ntp-deviations-NE8000-F1A";
  prefix ntp-devs-NE8000-F1A;

  import huawei-ntp {
    prefix ntp;
  }

  organization
    "Huawei Technologies Co., Ltd.";
  contact
    "Huawei Industrial Base
     Bantian, Longgang
     Shenzhen 518129
     People's Republic of China
     Website: http://www.huawei.com
     Email: support@huawei.com";
  description
    "This module defines deviation statements for huawei-ntp module.";

  revision 2021-05-07 {
    description
      "Initial revision.";
    reference "Huawei private.";
  }

  deviation "/ntp:ntp/ntp:board-statuses" {
    deviate not-supported;
  }
  deviation "/ntp:ntp/ntp:system-config/ntp:is-auth-password-check" {
    deviate replace {
      default "false";
    }
  }
  deviation "/ntp:ntp/ntp:access-controls/ntp:access-control" {
    deviate add {
      must 'acl4-identity or acl6-identity';
    }
  }
}
