/*
Copyright (C) 2021 Huawei Technologies Co., Ltd. All rights reserved.
*/
module huawei-bfd-static-mpls-te-deviations-NE8000-F1A {
  namespace "urn:huawei:yang:huawei-bfd-static-mpls-te-deviations-NE8000-F1A";
  prefix bfd-static-mpls-te-devs-NE8000-F1A;

  import huawei-bfd-static-mpls-te {
    prefix bfd-static-mpls-te;
  }
  import huawei-bfd {
    prefix bfd;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd-static-mpls-te module.";

  revision 2021-05-07 {
    description
      "Initial revision.";
    reference "Huawei private.";
  }

  deviation "/bfd:bfd/bfd:sessions/bfd:session/bfd:session-type/bfd:static/bfd:static-session-link-type/bfd-static-mpls-te:te-tunnel/bfd-static-mpls-te:select-board-slot-static-te-tunnel" {
    deviate not-supported;
  }
  deviation "/bfd:bfd/bfd:sessions/bfd:session/bfd-static-mpls-te:mpls-te-groups" {
    deviate not-supported;
  }
  deviation "/bfd:bfd/bfd:sessions/bfd:session/bfd:session-type/bfd:static/bfd:static-session-link-type/bfd-static-mpls-te:te-lsp/bfd-static-mpls-te:is-group-static-te-lsp" {
    deviate add {
      must "../bfd-static-mpls-te:is-group-static-te-lsp='false'";
    }
  }
  deviation "/bfd:bfd/bfd:sessions/bfd:session/bfd:session-type/bfd:static/bfd:static-session-link-type/bfd-static-mpls-te:te-tunnel/bfd-static-mpls-te:is-group-static-te-tunnel" {
    deviate add {
      must "../bfd-static-mpls-te:is-group-static-te-tunnel='false'";
    }
  }
}
