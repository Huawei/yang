/*
Copyright (C) 2021 Huawei Technologies Co., Ltd. All rights reserved.
*/
module huawei-qos-notification-deviations-NE8000-F1A {
  namespace "urn:huawei:yang:huawei-qos-notification-deviations-NE8000-F1A";
  prefix qos-notification-devs-NE8000-F1A;

  import huawei-qos-notification {
    prefix qos-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-qos-notification module.";

  revision 2021-05-07 {
    description
      "Initial revision.";
    reference
      "Huawei private.";
  }

  deviation "/qos-notification:hqos-user-queue-apply-pir-fail-alarm" {
    deviate not-supported;
  }
  deviation "/qos-notification:hqos-user-queue-apply-pir-success-alarm" {
    deviate not-supported;
  }
  deviation "/qos-notification:hqos-user-queue-apply-pir-from-pool-fail-alarm" {
    deviate not-supported;
  }
  deviation "/qos-notification:hqos-user-queue-apply-pir-from-pool-success-alarm" {
    deviate not-supported;
  }
  deviation "/qos-notification:xqos-4queue-resource-over-alarm" {
    deviate not-supported;
  }
  deviation "/qos-notification:xqos-4queue-resource-over-alarm-resume" {
    deviate not-supported;
  }
  deviation "/qos-notification:xqos-4queue-resource-pre-alarm" {
    deviate not-supported;
  }
  deviation "/qos-notification:xqos-4queue-resource-pre-alarm-resume" {
    deviate not-supported;
  }
  deviation "/qos-notification:xqos-8queue-resource-over-alarm" {
    deviate not-supported;
  }
  deviation "/qos-notification:xqos-8queue-resource-over-alarm-resume" {
    deviate not-supported;
  }
  deviation "/qos-notification:xqos-8queue-resource-pre-alarm" {
    deviate not-supported;
  }
  deviation "/qos-notification:xqos-8queue-resource-pre-alarm-resume" {
    deviate not-supported;
  }
  deviation "/qos-notification:xqos-hard-pipe-apply-user-queue-fail-alarm" {
    deviate not-supported;
  }
  deviation "/qos-notification:xqos-hard-pipe-apply-user-queue-fail-alarm-resume" {
    deviate not-supported;
  }
  deviation "/qos-notification:xqos-hard-pipe-bandwidth-alarm" {
    deviate not-supported;
  }
  deviation "/qos-notification:xqos-hard-pipe-bandwidth-alarm-resume" {
    deviate not-supported;
  }
  deviation "/qos-notification:xqos-tm-performance-alarm" {
    deviate not-supported;
  }
  deviation "/qos-notification:xqos-tm-performance-alarm-resume" {
    deviate not-supported;
  }
  deviation "/qos-notification:xqos-mode-flexe-over-portshap-alarm" {
    deviate not-supported;
  }
  deviation "/qos-notification:xqos-mode-flexe-over-portshap-alarm-resume" {
    deviate not-supported;
  }
  deviation "/qos-notification:xqos-unsupported-feature-alarm" {
    deviate not-supported;
  }
  deviation "/qos-notification:xqos-unsupported-feature-alarm-resume" {
    deviate not-supported;
  }
  deviation "/qos-notification:xqos-user-queue-apply-pir-exhaust-alarm" {
    deviate not-supported;
  }
  deviation "/qos-notification:xqos-user-queue-apply-pir-exhaust-resume" {
    deviate not-supported;
  }
  deviation "/qos-notification:xqos-user-queue-apply-pir-pre-alarm" {
    deviate not-supported;
  }
  deviation "/qos-notification:xqos-user-queue-apply-pir-pre-resume" {
    deviate not-supported;
  }
  deviation "/qos-notification:xqos-user-queue-pir-adjust-alarm" {
    deviate not-supported;
  }
  deviation "/qos-notification:xqos-user-queue-pir-adjust-resume" {
    deviate not-supported;
  }
  deviation "/qos-notification:xqos-unsupported-action-alarm" {
    deviate not-supported;
  }
  deviation "/qos-notification:xqos-unsupported-action-resume" {
    deviate not-supported;
  }

}
