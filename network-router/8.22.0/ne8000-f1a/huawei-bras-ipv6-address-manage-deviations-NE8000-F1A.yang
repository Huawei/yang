/*
Copyright (C) 2021 Huawei Technologies Co., Ltd. All rights reserved.
*/
module huawei-bras-ipv6-address-manage-deviations-NE8000-F1A {
  namespace "urn:huawei:yang:huawei-bras-ipv6-address-manage-deviations-NE8000-F1A";
  prefix bras-ipv6-address-manage-devs-NE8000-F1A;

  import huawei-bras-ipv6-address-manage {
    prefix bras-ipv6-address-manage;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-ipv6-address-manage module.";

  revision 2021-05-07 {
    description
      "Initial revision.";
    reference
      "Huawei private.";
  }

  typedef prefix-type-deviations {
    type enumeration {
      enum "local" {
        value 1;
        description
          "Local type.";
      }
      enum "delegation" {
        value 2;
        description
          "Delegation type.";
      }
      enum "remote" {
        value 3;
        description
          "Remote type.";
      }
    }
    description
      "IPv6 prefix type.";
  }

  deviation "/bras-ipv6-address-manage:bras-ipv6-address-manage/bras-ipv6-address-manage:ipv6-prefixs/bras-ipv6-address-manage:ipv6-prefix/bras-ipv6-address-manage:local/bras-ipv6-address-manage:occupied-policy" {
    deviate not-supported;
  }
  deviation "/bras-ipv6-address-manage:bras-ipv6-address-manage/bras-ipv6-address-manage:ipv6-prefixs/bras-ipv6-address-manage:ipv6-prefix/bras-ipv6-address-manage:delegation/bras-ipv6-address-manage:occupied-policy" {
    deviate not-supported;
  }
  deviation "/bras-ipv6-address-manage:bras-ipv6-address-manage/bras-ipv6-address-manage:ipv6-prefixs/bras-ipv6-address-manage:ipv6-prefix/bras-ipv6-address-manage:remote/bras-ipv6-address-manage:occupied-policy" {
    deviate not-supported;
  }
  deviation "/bras-ipv6-address-manage:bras-ipv6-address-manage/bras-ipv6-address-manage:ipv6-prefixs/bras-ipv6-address-manage:ipv6-prefix/bras-ipv6-address-manage:dynamic" {
    deviate not-supported;
  }
  deviation "/bras-ipv6-address-manage:bras-ipv6-address-manage/bras-ipv6-address-manage:ipv6-pools/bras-ipv6-address-manage:ipv6-pool/bras-ipv6-address-manage:cu-max-usages" {
    deviate not-supported;
  }
  deviation "/bras-ipv6-address-manage:bras-ipv6-address-manage/bras-ipv6-address-manage:statistics-by-domains/bras-ipv6-address-manage:statistics-by-domain/bras-ipv6-address-manage:cu-pool-usages" {
    deviate not-supported;
  }
  deviation "/bras-ipv6-address-manage:bras-ipv6-address-manage/bras-ipv6-address-manage:statistics-by-domains/bras-ipv6-address-manage:statistics-by-domain/bras-ipv6-address-manage:cu-max-usages" {
    deviate not-supported;
  }
  deviation "/bras-ipv6-address-manage:recycle-subnet" {
    deviate not-supported;
  }
  deviation "/bras-ipv6-address-manage:bras-ipv6-address-manage/bras-ipv6-address-manage:ipv6-prefixs/bras-ipv6-address-manage:ipv6-prefix/bras-ipv6-address-manage:type" {
    deviate replace {
      type bras-ipv6-address-manage-devs-NE8000-F1A:prefix-type-deviations;
    }
  }

}
