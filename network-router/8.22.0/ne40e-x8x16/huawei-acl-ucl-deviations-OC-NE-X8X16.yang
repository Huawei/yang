/*
Copyright (C) 2021 Huawei Technologies Co., Ltd. All rights reserved.
*/
module huawei-acl-ucl-deviations-OC-NE-X8X16 {
  namespace "urn:huawei:yang:huawei-acl-ucl-deviations-OC-NE-X8X16";
  prefix acl-ucl-devs-OC-NE-X8X16;

  import huawei-acl-ucl {
    prefix acl-ucl;
  }
  import huawei-acl {
    prefix acl;
  }

  organization
    "Huawei Technologies Co., Ltd.";
  contact
    "Huawei Industrial Base
     Bantian, Longgang
     Shenzhen 518129
     People's Republic of China
     Website: http://www.huawei.com
     Email: support@huawei.com";
  description
    "This module defines deviation statements for huawei-acl-ucl module.";

  revision 2021-05-07 {
    description
      "Initial revision.";
    reference "Huawei private.";
  }

  deviation "/acl:acl/acl:groups/acl:group/acl-ucl:rule-ucls/acl-ucl:rule-ucl/acl-ucl:source-group/acl-ucl:source-ucl-grp-name" {
    deviate not-supported;
  }
  deviation "/acl:acl/acl:groups/acl:group/acl-ucl:rule-ucls/acl-ucl:rule-ucl/acl-ucl:source-group/acl-ucl:source-ucl-grp-index" {
    deviate not-supported;
  }
  deviation "/acl:acl/acl:groups/acl:group/acl-ucl:rule-ucls/acl-ucl:rule-ucl/acl-ucl:dest-group/acl-ucl:dest-ucl-grp-name" {
    deviate not-supported;
  }
  deviation "/acl:acl/acl:groups/acl:group/acl-ucl:rule-ucls/acl-ucl:rule-ucl/acl-ucl:dest-group/acl-ucl:dest-ucl-grp-index" {
    deviate not-supported;
  }
  deviation "/acl:acl/acl:groups/acl:group/acl-ucl:rule-ucls/acl-ucl:rule-ucl/acl-ucl:vpn" {
    deviate not-supported;
  }
  deviation "/acl:acl/acl:group6s/acl:group6/acl-ucl:rule-ucls/acl-ucl:rule-ucl/acl-ucl:protocol-type/acl-ucl:zero" {
    deviate not-supported;
  }
}
