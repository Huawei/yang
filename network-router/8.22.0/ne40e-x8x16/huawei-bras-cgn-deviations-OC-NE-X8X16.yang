/*
Copyright (C) 2021 Huawei Technologies Co., Ltd. All rights reserved.
*/
module huawei-bras-cgn-deviations-OC-NE-X8X16 {
  namespace "urn:huawei:yang:huawei-bras-cgn-deviations-OC-NE-X8X16";
  prefix bras-cgn-devs-OC-NE-X8X16;

  import huawei-bras-cgn {
    prefix bras-cgn;
  }

  import huawei-aaa {
    prefix aaa;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-cgn module.";

  revision 2021-05-07 {
    description
      "Initial revision.";
    reference
      "Huawei private.";
  }

  deviation "/aaa:aaa/aaa:domains/aaa:domain/bras-basic-access:bas/bras-cgn:bras-cgn/bras-cgn:nat-distributed-policy" {
    deviate not-supported;
  }

}
