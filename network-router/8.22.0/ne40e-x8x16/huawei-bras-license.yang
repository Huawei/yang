/*
Copyright (C) 2020-2022 Huawei Technologies Co., Ltd. All rights reserved.
*/
module huawei-bras-license {
  namespace urn:huawei:yang:huawei-bras-license;
  prefix bras-license;
  import huawei-extension {
    prefix ext;
  }
  import huawei-devm {
    prefix devm;
  }
  import huawei-license {
    prefix lcs;
  }
  organization
    "Huawei Technologies Co., Ltd.";
  contact
    "Huawei Industrial Base
     Bantian, Longgang
     Shenzhen 518129
     People's Republic of China
     Website: http://www.huawei.com
     Email: support@huawei.com";
  description
    "Bras license.";

  revision 2022-09-09 {
    description
      "Modify description.";
    reference
      "Huawei private.";
  }

  revision 2020-12-15 {
    description
      "Initial revision.";
    reference
      "Huawei private.";
  }
  ext:task-name "license";

  typedef bras-license-feature-type {
    type enumeration {
      enum "access-pppoe" {
        value 1;
        description
          "Access PPPoE license.";
      }
    }
    description
      "Configures the bras license feature type.";
  }

  augment "/lcs:license" {
    description
      "Bas license configurations.";
    container bras-license {
      description
        "Configure Bras license.";
      container active-bas-slots {
        description
          "List of activate BAS on a board.";
        list active-bas-slot {
          key "slot-id";
          description
            "Configure activate BAS on a board.";
          leaf slot-id {
            type leafref {
              path "/devm:devm/devm:lpu-boards/devm:lpu-board/devm:position";
            }
            description
              "Specifies the slot ID of a board.";
          }
        }
      }
      container feature-resource-usages {
        config false;
        description
          "List of all license resource items by the feature.";
        list feature-resource-usage {
          key "feature-name";
          description
            "Operational state of license resource items by the feature.";
          leaf feature-name {
            type bras-license-feature-type;
            description
              "The feature name.";
          }
          container global-items {
            description
              "List of all global license resource items.";
            list global-item {
              key "item-name";
              description
                "Operational state of global license resource items.";
              leaf item-name {
                type string {
                  length "1..31";
                }
                description
                  "License item name.";
              }
              leaf description {
                type string {
                  length "1..255";
                }
                description
                  "The description of the license item.";
              }
              leaf total {
                type uint32;
                description
                  "Total number of license resources.";
                }
              leaf available {
                type uint32;
                description
                  "Number of remaining license resources that can be used.";
              }
            }
          }
        }
      }
    }
  }
}
