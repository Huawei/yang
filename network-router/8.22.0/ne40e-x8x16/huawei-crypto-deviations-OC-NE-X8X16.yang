/*
Copyright (C) 2021 Huawei Technologies Co., Ltd. All rights reserved.
*/
module huawei-crypto-deviations-OC-NE-X8X16 {
  namespace "urn:huawei:yang:huawei-crypto-deviations-OC-NE-X8X16";
  prefix crypto-devs-OC-NE-X8X16;

  import huawei-crypto {
    prefix crypto;
  }

  organization
    "Huawei Technologies Co., Ltd.";
  contact
    "Huawei Industrial Base
     Bantian, Longgang
     Shenzhen 518129
     People's Republic of China
     Website: http://www.huawei.com
     Email: support@huawei.com";
  description
    "This module defines deviation statements for huawei-crypto module.";

  revision 2021-05-07 {
    description
      "Initial revision.";
    reference "Huawei private.";
  }

  deviation "/crypto:crypto/crypto:fips-mode" {
    deviate not-supported;
  }
}
