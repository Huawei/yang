/*
Copyright (C) 2021 Huawei Technologies Co., Ltd. All rights reserved.
*/
module huawei-ietf-netconf-notifications-deviations-OC-NE-X8X16 {
  namespace "urn:huawei:yang:huawei-ietf-netconf-notifications-deviations-OC-NE-X8X16";
  prefix ncn-devs-OC-NE-X8X16;

  import ietf-netconf-notifications {
    prefix ncn;
  }

  organization
    "Huawei Technologies Co., Ltd.";
  contact
    "Huawei Industrial Base
     Bantian, Longgang
     Shenzhen 518129
     People's Republic of China
     Website: http://www.huawei.com
     Email: support@huawei.com";
  description
    "This module defines deviation statements for ietf-netconf-notifications module.";

  revision 2021-05-07 {
    description
      "Initial revision.";
    reference "Huawei private.";
  }

  deviation "/ncn:netconf-config-change/ncn:edit" {
    deviate not-supported;
  }
}
