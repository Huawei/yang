/*
Copyright (C) 2021 Huawei Technologies Co., Ltd. All rights reserved.
*/
module huawei-cgn-dslite-deviations-OC-NE-X8X16 {
  namespace "urn:huawei:yang:huawei-cgn-dslite-deviations-OC-NE-X8X16";
  prefix cgn-dslite-devs-OC-NE-X8X16;

  import huawei-cgn-dslite {
    prefix cgn-dslite;
  }

  organization
    "Huawei Technologies Co., Ltd.";

  contact
    "Huawei Industrial Base
     Bantian, Longgang
     Shenzhen 518129
     People's Republic of China
     Website: http://www.huawei.com
     Email: support@huawei.com";

  description
    "This module defines deviation statements for huawei-cgn-dslite module.";

  revision 2021-05-07 {
    description
      "Initial revision.";
    reference
      "Huawei private.";
  }

  typedef dslite-alg-protocol-type-deviations {
    type enumeration {
      enum "ftp" {
          value 1;
          description "Indicate file transfer protocol.";
      }
      enum "rtsp" {
          value 2;
          description "Indicate real time streaming protocol.";
      }
      enum "pptp" {
          value 4;
          description "Indicate point-to-point tunnel protocol.";
      }
      enum "sip" {
          value 8;
          description "Indicate session initiation protocol.";
      }
    }
    description
      "ALG Protocol.";
  }

  deviation "/cgn-dslite:cgn-dslite/cgn-dslite:dslite-instances/cgn-dslite:dslite-instance/cgn-dslite:log/cgn-dslite:hosts/cgn-dslite:host/cgn-dslite:inside-vpn-name" {
    deviate not-supported;
  }
  deviation "/cgn-dslite:cgn-dslite/cgn-dslite:dslite-instances/cgn-dslite:dslite-instance/cgn-dslite:statistics-enable/cgn-dslite:fast-forwarding" {
    deviate not-supported;
  }
  deviation "/cgn-dslite:cgn-dslite/cgn-dslite:dslite-instances/cgn-dslite:dslite-instance/cgn-dslite:algs/cgn-dslite:alg/cgn-dslite:protocol" {
    deviate replace {
      type cgn-dslite-devs-OC-NE-X8X16:dslite-alg-protocol-type-deviations;
    }
  }

}
