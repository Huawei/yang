/*
Copyright (C) 2021 Huawei Technologies Co., Ltd. All rights reserved.
*/
module huawei-system-notification-deviations-OC-NE-X8X16 {
  namespace "urn:huawei:yang:huawei-system-notification-deviations-OC-NE-X8X16";
  prefix system-notification-devs-OC-NE-X8X16;

  import huawei-system-notification {
    prefix system-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-system-notification module.";

  revision 2021-05-07 {
    description
      "Initial revision.";
    reference "Huawei private.";
  }

  deviation "/system-notification:security-risk" {
    deviate not-supported;
  }
  deviation "/system-notification:security-risk-clear" {
    deviate not-supported;
  }
}
