/*
Copyright (C) 2022 Huawei Technologies Co., Ltd. All rights reserved.
*/
module huawei-deterministic-ip-deviations-OC-NE-X8X16 {
  namespace "urn:huawei:yang:huawei-deterministic-ip-deviations-OC-NE-X8X16";
  prefix deterministic-ip-devs-OC-NE-X8X16;

  import huawei-deterministic-ip {
    prefix deterministic-ip;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-deterministic-ip module.";

  revision 2022-02-20 {
    description
      "Initial revision.";
    reference
      "Huawei private.";
  }

  deviation "/devm:devm/devm:mpu-boards/devm:mpu-board/deterministic-ip:deterministic-ip" {
    deviate not-supported;
  }
}
