/*
Copyright (C) 2021 Huawei Technologies Co., Ltd. All rights reserved.
*/
module huawei-flowspec-deviations-OC-NE-X8X16 {
  namespace "urn:huawei:yang:huawei-flowspec-deviations-OC-NE-X8X16";
  prefix flowspec-devs-OC-NE-X8X16;

  import huawei-flowspec {
    prefix flowspec;
  }

  organization
    "Huawei Technologies Co., Ltd.";
  contact
    "Huawei Industrial Base
     Bantian, Longgang
     Shenzhen 518129
     People's Republic of China
     Website: http://www.huawei.com
     Email: support@huawei.com";
  description
    "This module defines deviation statements for huawei-flowspec module.";

  revision 2021-05-07 {
    description
      "Initial revision.";
    reference "Huawei private.";
  }

  deviation "/flowspec:flowspec/flowspec:ipv6-family/flowspec:interface-group-statisticss" {
    deviate not-supported;
  }
}
