/*
Copyright (C) 2019 Huawei Technologies Co., Ltd. All rights reserved.
*/
module huawei-driver-deviations-OC-NE-X8X16 {
  namespace "urn:huawei:yang:huawei-driver-deviations-OC-NE-X8X16";
  prefix driver-devs-OC-NE-X8X16;

  import huawei-driver {
    prefix driver;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-driver module.";

  revision 2019-11-06 {
    description
      "Initial revision.";
    reference
      "Huawei private.";
  }

  typedef fan-workmode-deviations {
    type enumeration {
      enum "auto" {
        value 1;
        description 
          "Automatic.";
      }
      enum "manual" {
        value 2;
        description 
          "Percent.";
      }
      enum "silent" {
        value 4;
        description 
          "Silent.";
      }
      enum "full" {
        value 5;
        description 
          "Full.";
      }
      enum "minimum-percent" {
        value 9;
        description 
          "Minimum-percent.";
      }
    }
    description 
      "Information of enum type fan-workmode.";
  }

  typedef pwr-supply-temp-type-deviations {
    type enumeration {
      enum "templow" {
        value 40;
        description 
          "40.";
      }
      enum "temphigh" {
        value 55;
        description 
          "55.";
      }
    }
    description 
      "Information of enum type pwr-supply-temp-type.";
  }

  typedef trap-type-deviations {
    type enumeration {
      enum "base-trap" {
        value 1;
        description 
          "Base-trap.";
      }
      enum "entity-trap" {
        value 4;
        description 
          "Entity-trap.";
      }
    }
    description 
      "Information of enum type trap-type.";
  }

  typedef energy-mode-type-deviations {
    type enumeration {
      enum "basic" {
        value 0;
        description
          "Basic.";
      }
      enum "standard" {
        value 1;
        description
          "Standard.";
      }
      enum "deep" {
        value 2;
        description
          "Deep.";
      }
      enum "optimal" {
        value 3;
        description
          "Optimal.";
      }
    }
    description
      "Information of enum type energy-mode-type.";
  }

  deviation "/driver:driver/driver:global-attribute/driver:dustproof-check" {
    deviate not-supported;
  }
  deviation "/driver:driver/driver:global-attribute/driver:optional-entity-fault-isolate" {
    deviate not-supported;
  }
  deviation "/driver:driver/driver:global-attribute/driver:pic-reload-cycle" {
    deviate not-supported;
  }
  deviation "/driver:driver/driver:global-attribute/driver:sampling-period" {
    deviate not-supported;
  }
  deviation "/driver:driver/driver:global-attribute/driver:system-mac-address" {
    deviate not-supported;
  }
  deviation "/driver:driver/driver:global-attribute/driver:system-mac-number" {
    deviate not-supported;
  }
  deviation "/driver:driver/driver:global-attribute/driver:temp-query-mode" {
    deviate not-supported;
  }
  deviation "/driver:driver/driver:global-attribute/driver:vlt-query-mode" {
    deviate not-supported;
  }
  deviation "/driver:driver/driver:global-attribute/driver:cur-work-mode" {
    deviate not-supported;
  }
  deviation "/driver:driver/driver:global-attribute/driver:next-work-mode" {
    deviate not-supported;
  }
  
  deviation "/driver:driver/driver:global-attribute/driver:warm-backup-states" {
    deviate not-supported;
  }
  deviation "/driver:driver/driver:global-attribute/driver:warm-backup-mode" {
    deviate not-supported;
  }
  deviation "/driver:driver/driver:global-attribute/driver:cur-device-work-mode" {
    deviate not-supported;
  }
  deviation "/driver:driver/driver:global-attribute/driver:next-device-work-mode" {
    deviate not-supported;
  }
  deviation "/driver:driver/driver:global-attribute/driver:cur-system-mode" {
    deviate not-supported;
  }
  deviation "/driver:driver/driver:global-attribute/driver:next-system-mode" {
    deviate not-supported;
  }
  deviation "/driver:driver/driver:global-attribute/driver:switch-port-mode" {
    deviate not-supported;
  }
  deviation "/driver:driver/driver:global-attribute/driver:usb-uart-status" {
    deviate not-supported;
  }
  deviation "/driver:driver/driver:global-attribute/driver:cur-system-mac-address" {
    deviate not-supported;
  }
  deviation "/driver:driver/driver:global-attribute/driver:cur-dcn-plane-mode" {
    deviate not-supported;
  }
  deviation "/driver:driver/driver:io-inspect-states" {
    deviate not-supported;
  }
  deviation "/driver:driver/driver:io-inspect-attributes" {
    deviate not-supported;
  }
  deviation "/driver:driver/driver:board-powers" {
    deviate not-supported;
  }
  deviation "/driver:driver/driver:rollback-attribute" {
    deviate not-supported;
  }
  deviation "/driver:driver/driver:inner-links/driver:inner-link/driver:physical-inner-links" {
    deviate not-supported;
  }
  deviation "/driver:set-usb-uart-stat" {
    deviate not-supported;
  }
  deviation "/driver:power-on-icu" {
    deviate not-supported;
  }
  deviation "/driver:power-off-icu" {
    deviate not-supported;
  }
  deviation "/driver:reset-icu-board" {
    deviate not-supported;
  }
  deviation "/driver:reset-cmu-board" {
    deviate not-supported;
  }
  deviation "/driver:rollback" {
    deviate not-supported;
  }
  deviation "/driver:set-next-work-mode" {
    deviate not-supported;
  }
  deviation "/driver:set-led-flash" {
    deviate not-supported;
  }
  deviation "/driver:set-slot-led-flash" {
    deviate not-supported;
  }
  deviation "/driver:set-run-led-flash-off" {
    deviate not-supported;
  }
  deviation "/driver:check-system-software/driver:output/driver:match-result" {
    deviate not-supported;
  }
  deviation "/driver:check-lcm-channel" {
    deviate not-supported;
  }
  deviation "/driver:sysmac-load/driver:input/driver:chassis-id" {
    deviate not-supported;
  }
  deviation "/driver:set-next-system-mode" {
    deviate not-supported;
  }
  deviation "/devm:devm/devm:chassiss/devm:chassis/driver:power-supply-attribute/driver:power-supply-alarm-limit" {
    deviate not-supported;
  }
  deviation "/devm:devm/devm:chassiss/devm:chassis/driver:dustproof-attribute" {
    deviate not-supported;
  }
  deviation "/devm:devm/driver:driver/driver:ccus" {
    deviate not-supported;
  }
  deviation "/devm:devm/driver:driver/driver:icus" {
    deviate not-supported;
  }
  deviation "/devm:devm/driver:driver/driver:power-supplys/driver:power-supply/driver:power-environments/driver:power-environment/driver:out-voltage-value" {
    deviate not-supported;
  }
  deviation "/devm:devm/driver:driver/driver:power-supplys/driver:power-supply/driver:power-environments/driver:power-environment/driver:out-electrical-value" {
    deviate not-supported;
  }
  deviation "/devm:devm/driver:driver/driver:power-supplys/driver:power-supply/driver:power-environments/driver:power-environment/driver:out-power-value" {
    deviate not-supported;
  }
  deviation "/driver:driver/driver:global-attribute/driver:least-sfu-number" {
    deviate replace {
      type uint32 {
        range "1..4";
      }
    }
  }
  deviation "/driver:driver/driver:global-attribute/driver:system-trap" {
    deviate replace {
      type driver-devs-OC-NE-X8X16:trap-type-deviations;
    }
  }
  deviation "/driver:driver/driver:temperatures/driver:temperature" {
    deviate add {
      must "(minor and major and fatal) or (not(minor) and not(major) and not(fatal))";
    }
  }
  deviation "/driver:driver/driver:voltageinfos/driver:voltageinfo" {
    deviate add {
      must "(major-voltage-threshold-low and major-voltage-threshold-high and fatal-voltage-threshold-low and fatal-voltage-threshold-high) or (not(major-voltage-threshold-low) and not(major-voltage-threshold-high) and not(fatal-voltage-threshold-low) and not(fatal-voltage-threshold-high))";
    }
  }
  deviation "/devm:devm/devm:chassiss/devm:chassis/driver:fan-attribute/driver:workmode" {
    deviate replace {
      type driver-devs-OC-NE-X8X16:fan-workmode-deviations;
    }
  }
  deviation "/devm:devm/devm:chassiss/devm:chassis/driver:power-supply-attribute/driver:power-supply-temp" {
    deviate replace {
      type driver-devs-OC-NE-X8X16:pwr-supply-temp-type-deviations;
    }
  }
  deviation "/devm:devm/devm:chassiss/devm:chassis/driver:power-supply-attribute" {
    deviate add {
       must "not (power-supply-mode='assign' and not (power-supply-input))";
    }
  }
  deviation /driver:check-hardware-version/driver:input/driver:chassis-id {
    deviate not-supported;
  }
  deviation /devm:devm/devm:chassiss/devm:chassis/driver:chassis-id {
    deviate not-supported;
  }
  deviation /devm:devm/devm:chassiss/devm:chassis/driver:chassis-run-mode {
    deviate not-supported;
  }
  deviation /driver:set-next-run-mode {
    deviate not-supported;
  }
  deviation /driver:set-next-chassis-id {
    deviate not-supported;
  } 
  deviation /devm:devm/devm:chassiss/devm:chassis/driver:pm-input-attribute {
    deviate not-supported;
  }
  deviation /driver:set-power-pm-input-mode {
    deviate not-supported;
  } 
  deviation /driver:refresh-power-pm-input {
    deviate not-supported;
  } 
  deviation /driver:driver/driver:cluster-fiber {
    deviate not-supported;
  }
  deviation /driver:driver/driver:leds {
    deviate not-supported;
  }
  deviation /driver:set-next-fiber-connect-mode {
    deviate not-supported;
  }
 deviation "/driver:driver/driver:global-attribute/driver:energy-mode" {
    deviate replace {
      type driver-devs-OC-NE-X8X16:energy-mode-type-deviations;
    }    
  }
  deviation "/driver:driver/driver:area-energyinfos/driver:area-energyinfo/driver:area-real-power" {
    deviate not-supported;
  }
  deviation "/driver:driver/driver:area-energyinfos/driver:area-energyinfo/driver:area-power-mode" {
    deviate not-supported;
  }
  deviation "/devm:devm/devm:chassiss/devm:chassis/driver:fan-attribute/driver:area-fan-attributes" {
    deviate not-supported;
  }
  deviation "/devm:devm/driver:driver/driver:fans/driver:fan/driver:area-id" {
    deviate not-supported;
  }
  deviation "/driver:driver/driver:power-global-attribute" {
    deviate not-supported;
  }
}
