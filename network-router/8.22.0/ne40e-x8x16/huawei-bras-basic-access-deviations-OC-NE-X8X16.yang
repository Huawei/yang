/*
Copyright (C) 2021 Huawei Technologies Co., Ltd. All rights reserved.
*/
module huawei-bras-basic-access-deviations-OC-NE-X8X16 {
  namespace "urn:huawei:yang:huawei-bras-basic-access-deviations-OC-NE-X8X16";
  prefix bras-basic-access-devs-OC-NE-X8X16;

  import huawei-bras-basic-access {
    prefix bras-basic-access;
  }

  import huawei-ifm {
    prefix ifm;
  }

  import huawei-bras-cu-controller {
    prefix bras-cu-controller;
  }

  import huawei-devm-vnf {
    prefix devm-vnf;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-basic-access module.";

  revision 2021-05-07 {
    description
      "Initial revision.";
    reference
      "Huawei private.";
  }

  deviation "/bras-basic-access:bras-basic-access/bras-basic-access:carry-up-id" {
    deviate not-supported;
  }
  deviation "/ifm:ifm/ifm:interfaces/ifm:interface/bras-basic-access:bas/bras-basic-access:access-type/bras-basic-access:layer2-subscriber/bras-basic-access:layer2-subscriber/bras-basic-access:access-delay/bras-basic-access:access-delay/bras-basic-access:backup" {
    deviate not-supported;
  }
  deviation "/ifm:ifm/ifm:interfaces/ifm:interface/bras-basic-access:bas/bras-basic-access:access-type/bras-basic-access:layer2-leaseline/bras-basic-access:layer2-leaseline/bras-basic-access:access-delay/bras-basic-access:access-delay/bras-basic-access:backup" {
    deviate not-supported;
  }
  deviation "/devm:devm/devm:mpu-boards/devm:mpu-board/bras-basic-access:bras" {
    deviate not-supported;
  }
  deviation "/devm-vnf:devm-vnf/devm-vnf:vnf-boards/devm-vnf:vnf-board/bras-basic-access:bras" {
    deviate not-supported;
  }
  deviation "/bras-cu-controller:bras-cu-controller/bras-cu-controller:resource-ups/bras-cu-controller:resource-up/bras-cu-controller:remote-up-boards/bras-cu-controller:remote-up-board/bras-basic-access:bras" {
    deviate not-supported;
  }

}
