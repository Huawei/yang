/*
Copyright (C) 2021 Huawei Technologies Co., Ltd. All rights reserved.
*/
module huawei-bras-vas-deviations-OC-NE-X8X16 {
  namespace "urn:huawei:yang:huawei-bras-vas-deviations-OC-NE-X8X16";
  prefix bras-vas-devs-OC-NE-X8X16;

  import huawei-bras-vas {
    prefix bras-vas;
  }

  import huawei-bras-cu-controller {
    prefix bras-cu-controller;
  }

  import huawei-devm-vnf {
    prefix devm-vnf;
  }

  import huawei-devm {
    prefix devm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-vas module.";

  revision 2021-05-07 {
    description
      "Initial revision.";
    reference
      "Huawei private.";
  }

  deviation "/devm:devm/devm:mpu-boards/devm:mpu-board/bras-basic-access:bras/bras-vas:vas" {
    deviate not-supported;
  }
  deviation "/devm-vnf:devm-vnf/devm-vnf:vnf-boards/devm-vnf:vnf-board/bras-basic-access:bras/bras-vas:vas" {
    deviate not-supported;
  }
  deviation "/bras-cu-controller:bras-cu-controller/bras-cu-controller:resource-ups/bras-cu-controller:resource-up/bras-cu-controller:remote-up-boards/bras-cu-controller:remote-up-board/bras-basic-access:bras/bras-vas:vas" {
    deviate not-supported;
  }

}
