/*
Copyright (C) 2021 Huawei Technologies Co., Ltd. All rights reserved.
*/
module huawei-nqa-notification-deviations-OC-NE-X8X16 {
  namespace "urn:huawei:yang:huawei-nqa-notification-deviations-OC-NE-X8X16";
  prefix nqa-notification-devs-OC-NE-X8X16;

  import huawei-nqa-notification {
    prefix nqa-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-nqa-notification module.";

  revision 2021-05-07 {
    description
      "Initial revision.";
    reference "Huawei private.";
  }

  deviation "/nqa-notification:ping-test-failed" {
    deviate not-supported;
  }
}
