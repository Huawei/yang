/*
Copyright (C) 2019 Huawei Technologies Co., Ltd. All rights reserved.
*/
module huawei-lspic-tdm-deviations-OC-NE-X8X16 {
  namespace "urn:huawei:yang:huawei-lspic-tdm-deviations-OC-NE-X8X16";
  prefix lspic-tdm-devs-OC-NE-X8X16;

  import huawei-lspic-tdm {
    prefix lspic-tdm;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-lspic-tdm module.";

  revision 2019-11-06 {
    description
      "Initial revision.";
    reference
      "Huawei private.";
  }

  deviation "/lspic-tdm:time-delay-measurement-start" {
    deviate not-supported;
  }
  deviation "/lspic-tdm:select-receiving-stream" {
    deviate not-supported;
  }
  deviation "/ifm:ifm/ifm:interfaces/ifm:interface/lspic-tdm:tdm/lspic-tdm:channel-serial/lspic-tdm:underrun-checktimes" {
    deviate not-supported;
  }
  deviation "/ifm:ifm/ifm:interfaces/ifm:interface/lspic-tdm:tdm/lspic-tdm:channel-serial/lspic-tdm:stream-select-state" {
    deviate not-supported;
  }
  deviation "/ifm:ifm/ifm:interfaces/ifm:interface/lspic-tdm:tdm/lspic-tdm:phy-serial" {
    deviate not-supported;
  }
  deviation "/ifm:ifm/ifm:interfaces/ifm:interface/lspic-tdm:tdm" {
    deviate delete {
      must "not (channel-serial and phy-serial)";
    }
  }

}
