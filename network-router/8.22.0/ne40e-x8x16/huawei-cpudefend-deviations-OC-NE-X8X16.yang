/*
Copyright (C) 2021 Huawei Technologies Co., Ltd. All rights reserved.
*/
module huawei-cpudefend-deviations-OC-NE-X8X16 {
  namespace "urn:huawei:yang:huawei-cpudefend-deviations-OC-NE-X8X16";
  prefix cpudefend-devs-OC-NE-X8X16;

  import huawei-cpudefend {
    prefix cpudefend;
  }

  import huawei-extension {
    prefix ext;
  }

  import huawei-ifm {
    prefix ifm;
  }

  import huawei-devm-vnf {
    prefix devm-vnf;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-cpudefend module.";

  revision 2021-05-07 {
    description
      "Initial revision.";
    reference
      "Huawei private.";
  }

  typedef link-type-deviations {
    type enumeration {
      enum "ethernet" {
        value 1;
        description 
          "ETHERNET Protocol.";
      }
      enum "ppp" {
        value 2;
        description 
          "PPP Protocol.";
      }
      enum "hdlc" {
        value 3;
        description 
          "HDLC Protocol.";
      }
    }
    description 
      "Link type.";
  }

  typedef protocol-group-deviations {
    type enumeration {
      enum "whitelist" {
        value 1;
        description 
          "Group of authorized users or high-priority users.";
      }
      enum "user-defined-flow" {
        value 2;
        description 
          "User-defined flows.";
      }
      enum "management" {
        value 3;
        description 
          "Management packets.";
      }
      enum "route" {
        value 4;
        description 
          "Routing protocol packets.";
      }
      enum "multicast" {
        value 5;
        description 
          "Multicast packets.";
      }
      enum "arp" {
        value 6;
        description 
          "ARP packets.";
      }
      enum "mpls" {
        value 7;
        description 
          "MPLS packets.";
      }
      enum "access-user" {
        value 8;
        description 
          "Access packets.";
      }
      enum "link-layer" {
        value 9;
        description 
          "Data link layer packets, including connectivity packets and reliability packets.
          Data link layer packets also include protocol packets that influence services and links on the data link layer.";
      }
      enum "network-layer" {
        value 10;
        description 
          "Network layer packets, including entries that the forwarding plane instructs the control plane to deliver.";
      }
      enum "system-message" {
        value 12;
        description 
          "System-message.";
      }
      enum "blacklist" {
        value 13;
        description 
          "Blacklist.";
      }
      enum "check-failed" {
        value 14;
        description 
          "Check-failed.";
      }
      enum "fwddata-to-cp" {
        value 15;
        description 
          "Fwddata-to-cp packets.";
      }
    }
    description 
      "Protocol group.";
  }

  typedef protocol-name-deviations {
    type enumeration {
      enum "802dot1ag" {
        value 1;
        description 
          "802.1AG protocol.";
      }
      enum "arp" {
        value 3;
        description 
          "ARP protocol.";
      }
      enum "arp-miss" {
        value 4;
        description 
          "ARP miss protocol.";
      }
      enum "bfd" {
        value 6;
        description 
          "BFD protocol.";
      }
      enum "bgp" {
        value 7;
        description 
          "BGP protocol.";
      }
      enum "bgpv6" {
        value 8;
        description 
          "BGPv6 protocol.";
      }
      enum "blacklist" {
        value 9;
        description 
          "Blacklist.";
      }
      enum "bpdu" {
        value 10;
        description 
          "BPDU protocol.";
      }
      enum "dhcp" {
        value 15;
        description 
          "DHCP protocol.";
      }
      enum "dhcpv6" {
        value 16;
        description 
          "DHCPv6 protocol.";
      }
      enum "diameter" {
        value 17;
        description 
          "Diameter protocol.";
      }
      enum "dns-client" {
        value 18;
        description 
          "DNS client protocol.";
      }
      enum "dnsv6" {
        value 19;
        description 
          "DNSv6 protocol.";
      }
      enum "eapol" {
        value 20;
        description 
          "EAPOL protocol.";
      }
      enum "fragment" {
        value 21;
        description 
          "Fragment protocol.";
      }
      enum "ftp-client" {
        value 22;
        description 
          "FTP client protocol.";
      }
      enum "ftp-server" {
        value 23;
        description 
          "FTP server protocol.";
      }
      enum "ftpv6-client" {
        value 24;
        description 
          "FTPv6 client protocol.";
      }
      enum "ftpv6-server" {
        value 25;
        description 
          "FTPv6 server protocol.";
      }
      enum "http-redirect-chasten" {
        value 27;
        description 
          "Http-redirect packet of chasten user.";
      }
      enum "hwtacacs" {
        value 28;
        description 
          "HWTACACS protocol.";
      }
      enum "icmp" {
        value 29;
        description 
          "ICMP protocol.";
      }
      enum "icmp-broadcast-address-echo" {
        value 30;
        description 
          "Broadcast ICMP echo request packets.";
      }
      enum "icmpv6" {
        value 33;
        description 
          "ICMPv6 protocol.";
      }
      enum "icmpv6-na" {
        value 34;
        description 
          "ICMPv6-NA protocol.";
      }
      enum "icmpv6-ns" {
        value 35;
        description 
          "ICMPv6-NS protocol.";
      }
      enum "icmpv6-ra" {
        value 36;
        description 
          "ICMPv6-RA protocol.";
      }
      enum "icmpv6-rs" {
        value 37;
        description 
          "ICMPv6-RS protocol.";
      }
      enum "igmp" {
        value 38;
        description 
          "IGMP protocol.";
      }
      enum "ipv4-fib-miss" {
        value 41;
        description 
          "IPv4 FIB miss.";
      }
      enum "ipv4-multicast-fib-miss" {
        value 42;
        description 
          "IPv4 multicast FIB miss.";
      }
      enum "ipv4-ttl-expire" {
        value 43;
        description 
          "IPv4 TTL expires packets.";
      }
      enum "ipv6-fib-miss" {
        value 44;
        description 
          "IPv6 FIB miss.";
      }
      enum "ipv6-nd-miss" {
        value 46;
        description 
          "IPv6 ND miss.";
      }
      enum "ipv6-ttl-expire" {
        value 47;
        description 
          "IPv6 TTL expires packets.";
      }
      enum "isis" {
        value 48;
        description 
          "ISIS protocol.";
      }
      enum "lacp" {
        value 49;
        description 
          "LACP protocol.";
      }
      enum "ldp" {
        value 50;
        description 
          "LDP protocol.";
      }
      enum "lldp" {
        value 51;
        description 
          "LLDP protocol.";
      }
      enum "lspping" {
        value 52;
        description 
          "LSPPING protocol.";
      }
      enum "mka" {
        value 53;
        description 
          "MKA protocol.";
      }
      enum "mld" {
        value 54;
        description 
          "IPv6 MLD protocol.";
      }
      enum "mpls-arp-miss" {
        value 55;
        description 
          "MPLS ARP miss.";
      }
      enum "mpls-ttl-expire" {
        value 58;
        description 
          "MPLS ttl expires packets.";
      }
      enum "msdp" {
        value 59;
        description 
          "MSDP protocol.";
      }
      enum "netstream" {
        value 61;
        description 
          "NetStream protocol.";
      }
      enum "ntp" {
        value 62;
        description 
          "NTP protocol.";
      }
      enum "openflow" {
        value 63;
        status deprecated;
        description 
          "Open-Flow protocol. The enum openflow is deprecated. You are advised to use '/cpudefend:typedef (protocol-name)[enum (cusp)]'.";
      }
      enum "ospf" {
        value 64;
        description 
          "OSPF protocol.";
      }
      enum "ospfv3" {
        value 65;
        description 
          "OSPFv3 protocol.";
      }
      enum "pim" {
        value 66;
        description 
          "PIM protocol.";
      }
      enum "pimv6" {
        value 67;
        description 
          "PIMv6 protocol.";
      }
      enum "portal" {
        value 68;
        description 
          "Portal protocol.";
      }
      enum "radius" {
        value 70;
        description 
          "Radius protocol.";
      }
      enum "rip" {
        value 71;
        description 
          "RIP protocol.";
      }
      enum "rsvp" {
        value 73;
        description 
          "RSVP protocol.";
      }
      enum "snmp" {
        value 74;
        description 
          "SNMP protocol.";
      }
      enum "snmpv6" {
        value 75;
        description 
          "SNMPv6 protocol.";
      }
      enum "soft-gre" {
        value 76;
        description 
          "Soft GRE protocol.";
      }
      enum "ssh-client" {
        value 77;
        description 
          "SSH client protocol.";
      }
      enum "ssh-server" {
        value 78;
        description 
          "SSH server protocol.";
      }
      enum "sshv6-server" {
        value 79;
        description 
          "SSHv6 server protocol.";
      }
      enum "syslog" {
        value 80;
        description 
          "SYSLOG protocol.";
      }
      enum "tcpsyn" {
        value 81;
        description 
          "TCP SYN protocol.";
      }
      enum "telnet-client" {
        value 82;
        description 
          "TELNET client protocol.";
      }
      enum "telnet-server" {
        value 83;
        description 
          "TELNET server protocol.";
      }
      enum "telnetv6-client" {
        value 84;
        description 
          "TELNETv6 client protocol.";
      }
      enum "telnetv6-server" {
        value 85;
        description 
          "TELNETv6 server protocol.";
      }
      enum "tftp" {
        value 86;
        description 
          "TFTP protocol.";
      }
      enum "tftpv6-client" {
        value 87;
        description 
          "TFTPv6 client protocol.";
      }
      enum "traffic-behavior-log" {
        value 88;
        description 
          "Traffic Behavior Log.";
      }
      enum "unicast-vrrp" {
        value 89;
        description 
          "Unicast VRRP protocol.";
      }
      enum "user-defined-flow-1" {
        value 90;
        description 
          "User defined flow 1.";
      }
      enum "user-defined-flow-2" {
        value 91;
        description 
          "User defined flow 2.";
      }
      enum "user-defined-flow-3" {
        value 92;
        description 
          "User defined flow 3.";
      }
      enum "user-defined-flow-4" {
        value 93;
        description 
          "User defined flow 4.";
      }
      enum "user-defined-flow-5" {
        value 94;
        description 
          "User defined flow 5.";
      }
      enum "user-defined-flow-6" {
        value 95;
        description 
          "User defined flow 6.";
      }
      enum "user-defined-flow-7" {
        value 96;
        description 
          "User defined flow 7.";
      }
      enum "user-defined-flow-8" {
        value 97;
        description 
          "User defined flow 8.";
      }
      enum "user-defined-flow-9" {
        value 98;
        description 
          "User defined flow 9.";
      }
      enum "user-defined-flow-10" {
        value 99;
        description 
          "User defined flow 10.";
      }
      enum "user-defined-flow-11" {
        value 100;
        description 
          "User defined flow 11.";
      }
      enum "user-defined-flow-12" {
        value 101;
        description 
          "User defined flow 12.";
      }
      enum "user-defined-flow-13" {
        value 102;
        description 
          "User defined flow 13.";
      }
      enum "user-defined-flow-14" {
        value 103;
        description 
          "User defined flow 14.";
      }
      enum "user-defined-flow-15" {
        value 104;
        description 
          "User defined flow 15.";
      }
      enum "user-defined-flow-16" {
        value 105;
        description 
          "User defined flow 16.";
      }
      enum "user-defined-flow-17" {
        value 106;
        description 
          "User defined flow 17.";
      }
      enum "user-defined-flow-18" {
        value 107;
        description 
          "User defined flow 18.";
      }
      enum "user-defined-flow-19" {
        value 108;
        description 
          "User defined flow 19.";
      }
      enum "user-defined-flow-20" {
        value 109;
        description 
          "User defined flow 20.";
      }
      enum "user-defined-flow-21" {
        value 110;
        description 
          "User defined flow 21.";
      }
      enum "user-defined-flow-22" {
        value 111;
        description 
          "User defined flow 22.";
      }
      enum "user-defined-flow-23" {
        value 112;
        description 
          "User defined flow 23.";
      }
      enum "user-defined-flow-24" {
        value 113;
        description 
          "User defined flow 24.";
      }
      enum "user-defined-flow-25" {
        value 114;
        description 
          "User defined flow 25.";
      }
      enum "user-defined-flow-26" {
        value 115;
        description 
          "User defined flow 26.";
      }
      enum "user-defined-flow-27" {
        value 116;
        description 
          "User defined flow 27.";
      }
      enum "user-defined-flow-28" {
        value 117;
        description 
          "User defined flow 28.";
      }
      enum "user-defined-flow-29" {
        value 118;
        description 
          "User defined flow 29.";
      }
      enum "user-defined-flow-30" {
        value 119;
        description 
          "User defined flow 30.";
      }
      enum "user-defined-flow-31" {
        value 120;
        description 
          "User defined flow 31.";
      }
      enum "user-defined-flow-32" {
        value 121;
        description 
          "User defined flow 32.";
      }
      enum "user-defined-flow-33" {
        value 122;
        description 
          "User defined flow 33.";
      }
      enum "user-defined-flow-34" {
        value 123;
        description 
          "User defined flow 34.";
      }
      enum "user-defined-flow-35" {
        value 124;
        description 
          "User defined flow 35.";
      }
      enum "user-defined-flow-36" {
        value 125;
        description 
          "User defined flow 36.";
      }
      enum "user-defined-flow-37" {
        value 126;
        description 
          "User defined flow 37.";
      }
      enum "user-defined-flow-38" {
        value 127;
        description 
          "User defined flow 38.";
      }
      enum "user-defined-flow-39" {
        value 128;
        description 
          "User defined flow 39.";
      }
      enum "user-defined-flow-40" {
        value 129;
        description 
          "User defined flow 40.";
      }
      enum "user-defined-flow-41" {
        value 130;
        description 
          "User defined flow 41.";
      }
      enum "user-defined-flow-42" {
        value 131;
        description 
          "User defined flow 42.";
      }
      enum "user-defined-flow-43" {
        value 132;
        description 
          "User defined flow 43.";
      }
      enum "user-defined-flow-44" {
        value 133;
        description 
          "User defined flow 44.";
      }
      enum "user-defined-flow-45" {
        value 134;
        description 
          "User defined flow 45.";
      }
      enum "user-defined-flow-46" {
        value 135;
        description 
          "User defined flow 46.";
      }
      enum "user-defined-flow-47" {
        value 136;
        description 
          "User defined flow 47.";
      }
      enum "user-defined-flow-48" {
        value 137;
        description 
          "User defined flow 48.";
      }
      enum "user-defined-flow-49" {
        value 138;
        description 
          "User defined flow 49.";
      }
      enum "user-defined-flow-50" {
        value 139;
        description 
          "User defined flow 50.";
      }
      enum "user-defined-flow-51" {
        value 140;
        description 
          "User defined flow 51.";
      }
      enum "user-defined-flow-52" {
        value 141;
        description 
          "User defined flow 52.";
      }
      enum "user-defined-flow-53" {
        value 142;
        description 
          "User defined flow 53.";
      }
      enum "user-defined-flow-54" {
        value 143;
        description 
          "User defined flow 54.";
      }
      enum "user-defined-flow-55" {
        value 144;
        description 
          "User defined flow 55.";
      }
      enum "user-defined-flow-56" {
        value 145;
        description 
          "User defined flow 56.";
      }
      enum "user-defined-flow-57" {
        value 146;
        description 
          "User defined flow 57.";
      }
      enum "user-defined-flow-58" {
        value 147;
        description 
          "User defined flow 58.";
      }
      enum "user-defined-flow-59" {
        value 148;
        description 
          "User defined flow 59.";
      }
      enum "user-defined-flow-60" {
        value 149;
        description 
          "User defined flow 60.";
      }
      enum "user-defined-flow-61" {
        value 150;
        description 
          "User defined flow 61.";
      }
      enum "user-defined-flow-62" {
        value 151;
        description 
          "User defined flow 62.";
      }
      enum "user-defined-flow-63" {
        value 152;
        description 
          "User defined flow 63.";
      }
      enum "user-defined-flow-64" {
        value 153;
        description 
          "User defined flow 64.";
      }
      enum "vrrp" {
        value 154;
        description 
          "VRRP protocol.";
      }
      enum "web" {
        value 155;
        description 
          "Web protocol.";
      }
      enum "web-auth-server" {
        value 156;
        description 
          "Web authentication server protocol.";
      }
      enum "whitelist" {
        value 157;
        description 
          "Whitelist.";
      }
      enum "whitelist-bgp" {
        value 158;
        description 
          "Whitelist of BGP protocol.";
      }
      enum "whitelist-isis" {
        value 159;
        description 
          "Whitelist of ISIS protocol.";
      }
      enum "whitelist-ldp" {
        value 160;
        description 
          "Whitelist of LDP protocol.";
      }
      enum "whitelist-ospf" {
        value 161;
        description 
          "Whitelist of OSPF protocol.";
      }
      enum "whitelist-radius" {
        value 162;
        description 
          "Whitelist of Radius protocol.";
      }
      enum "whitelist-rsvp" {
        value 163;
        description 
          "Whitelist of RSVP protocol.";
      }
      enum "whitelistv6" {
        value 164;
        description 
          "IPv6 whitelist.";
      }
      enum "whitelistv6-bgpv6" {
        value 165;
        description 
          "IPv6 whitelist of BGPv6 protocol.";
      }
      enum "whitelistv6-ospfv3" {
        value 166;
        description 
          "IPv6 whitelist of OSPFv3 protocol.";
      }
      enum "hwtacacsv6" {
        value 167;
        description 
          "HWTACACSV6 protocol.";
      }
      enum "lsppingv6" {
        value 168;
        description 
          "Lsppingv6 packet.";
      }
      enum "pcep" {
        value 169;
        description 
          "Pcep packet.";
      }
      enum "radiusv6" {
        value 170;
        description 
          "Radiusv6 packet.";
      }
      enum "syslogv6" {
        value 171;
        description 
          "Syslogv6 packet.";
      }
      enum "vrrpv6" {
        value 172;
        description 
          "Vrrpv6 packet.";
      }
      enum "web-auth-serverv6" {
        value 173;
        description 
          "Web-auth-serverv6 packet.";
      }
      enum "cusp" {
        value 176;
        description 
          "Cusp packet.";
      }
    }
    description 
      "Protocol name.";
  }

  typedef protocol-name-reset-deviations {
    type enumeration {
      enum "802dot1ag" {
        value 1;
        description 
          "802.1AG protocol.";
      }
      enum "arp" {
        value 3;
        description 
          "ARP protocol.";
      }
      enum "arp-miss" {
        value 4;
        description 
          "ARP miss protocol.";
      }
      enum "bfd" {
        value 6;
        description 
          "BFD protocol.";
      }
      enum "bgp" {
        value 7;
        description 
          "BGP protocol.";
      }
      enum "bgpv6" {
        value 8;
        description 
          "BGPv6 protocol.";
      }
      enum "bpdu" {
        value 9;
        description 
          "BPDU protocol.";
      }
      enum "dhcp" {
        value 14;
        description 
          "DHCP protocol.";
      }
      enum "dhcpv6" {
        value 15;
        description 
          "DHCPv6 protocol.";
      }
      enum "diameter" {
        value 16;
        description 
          "Diameter protocol.";
      }
      enum "dns-client" {
        value 17;
        description 
          "DNS client protocol.";
      }
      enum "dnsv6" {
        value 18;
        description 
          "DNSv6 protocol.";
      }
      enum "eapol" {
        value 19;
        description 
          "EAPOL protocol.";
      }
      enum "ftp-client" {
        value 20;
        description 
          "FTP client protocol.";
      }
      enum "ftp-server" {
        value 21;
        description 
          "FTP server protocol.";
      }
      enum "ftpv6-client" {
        value 22;
        description 
          "FTPv6 client protocol.";
      }
      enum "ftpv6-server" {
        value 23;
        description 
          "FTPv6 server protocol.";
      }
      enum "http-redirect-chasten" {
        value 25;
        description 
          "Http-redirect packet of chasten user.";
      }
      enum "hwtacacs" {
        value 26;
        description 
          "HWTACACS protocol.";
      }
      enum "icmp" {
        value 27;
        description 
          "ICMP protocol.";
      }
      enum "icmp-broadcast-address-echo" {
        value 28;
        description 
          "Broadcast ICMP echo request packets.";
      }
      enum "icmpv6" {
        value 31;
        description 
          "ICMPv6 protocol.";
      }
      enum "icmpv6-na" {
        value 32;
        description 
          "ICMPv6-NA protocol.";
      }
      enum "icmpv6-ns" {
        value 33;
        description 
          "ICMPv6-NS protocol.";
      }
      enum "icmpv6-ra" {
        value 34;
        description 
          "ICMPv6-RA protocol.";
      }
      enum "icmpv6-rs" {
        value 35;
        description 
          "ICMPv6-RS protocol.";
      }
      enum "igmp" {
        value 36;
        description 
          "IGMP protocol.";
      }
      enum "ipv4-fib-miss" {
        value 39;
        description 
          "IPv4 FIB miss.";
      }
      enum "ipv4-multicast-fib-miss" {
        value 40;
        description 
          "IPv4 multicast FIB miss.";
      }
      enum "ipv4-ttl-expire" {
        value 41;
        description 
          "IPv4 TTL expires packets.";
      }
      enum "ipv6-fib-miss" {
        value 42;
        description 
          "IPv6 FIB miss.";
      }
      enum "ipv6-nd-miss" {
        value 44;
        description 
          "IPv6 ND miss.";
      }
      enum "ipv6-ttl-expire" {
        value 45;
        description 
          "IPv6 TTL expires packets.";
      }
      enum "isis" {
        value 46;
        description 
          "ISIS protocol.";
      }
      enum "lacp" {
        value 47;
        description 
          "LACP protocol.";
      }
      enum "ldp" {
        value 48;
        description 
          "LDP protocol.";
      }
      enum "lldp" {
        value 49;
        description 
          "LLDP protocol.";
      }
      enum "lspping" {
        value 50;
        description 
          "LSPPING protocol.";
      }
      enum "mka" {
        value 51;
        description 
          "MKA protocol.";
      }
      enum "mld" {
        value 52;
        description 
          "IPv6 MLD protocol.";
      }
      enum "mpls-arp-miss" {
        value 53;
        description 
          "MPLS ARP miss.";
      }
      enum "mpls-ttl-expire" {
        value 56;
        description 
          "MPLS ttl expires packets.";
      }
      enum "msdp" {
        value 57;
        description 
          "MSDP protocol.";
      }
      enum "netstream" {
        value 59;
        description 
          "NetStream protocol.";
      }
      enum "ntp" {
        value 60;
        description 
          "NTP protocol.";
      }
      enum "openflow" {
        value 61;
        status deprecated;
        description 
          "Open-Flow protocol. The enum openflow is deprecated. You are advised to use '/cpudefend:typedef (protocol-name-reset)[enum (cusp)]'.";
      }
      enum "ospf" {
        value 62;
        description 
          "OSPF protocol.";
      }
      enum "ospfv3" {
        value 63;
        description 
          "OSPFv3 protocol.";
      }
      enum "pim" {
        value 64;
        description 
          "PIM protocol.";
      }
      enum "pimv6" {
        value 65;
        description 
          "PIMv6 protocol.";
      }
      enum "portal" {
        value 66;
        description 
          "Portal protocol.";
      }
      enum "radius" {
        value 68;
        description 
          "Radius protocol.";
      }
      enum "rip" {
        value 69;
        description 
          "RIP protocol.";
      }
      enum "rsvp" {
        value 71;
        description 
          "RSVP protocol.";
      }
      enum "snmp" {
        value 72;
        description 
          "SNMP protocol.";
      }
      enum "snmpv6" {
        value 73;
        description 
          "SNMPv6 protocol.";
      }
      enum "soft-gre" {
        value 74;
        description 
          "Soft GRE protocol.";
      }
      enum "ssh-client" {
        value 75;
        description 
          "SSH client protocol.";
      }
      enum "ssh-server" {
        value 76;
        description 
          "SSH server protocol.";
      }
      enum "sshv6-server" {
        value 77;
        description 
          "SSHv6 server protocol.";
      }
      enum "syslog" {
        value 78;
        description 
          "SYSLOG protocol.";
      }
      enum "telnet-client" {
        value 79;
        description 
          "TELNET client protocol.";
      }
      enum "telnet-server" {
        value 80;
        description 
          "TELNET server protocol.";
      }
      enum "telnetv6-client" {
        value 81;
        description 
          "TELNETv6 client protocol.";
      }
      enum "telnetv6-server" {
        value 82;
        description 
          "TELNETv6 server protocol.";
      }
      enum "tftp" {
        value 83;
        description 
          "TFTP protocol.";
      }
      enum "tftpv6-client" {
        value 84;
        description 
          "TFTPv6 client protocol.";
      }
      enum "traffic-behavior-log" {
        value 85;
        description 
          "Traffic Behavior Log.";
      }
      enum "unicast-vrrp" {
        value 86;
        description 
          "Unicast VRRP protocol.";
      }
      enum "vrrp" {
        value 87;
        description 
          "VRRP protocol.";
      }
      enum "web" {
        value 88;
        description 
          "Web protocol.";
      }
      enum "web-auth-server" {
        value 89;
        description 
          "Web authentication server protocol.";
      }
      enum "hwtacacsv6" {
        value 90;
        description 
          "HWTACACSv6 protocol.";
      }
      enum "lsppingv6" {
        value 91;
        description 
          "Lsppingv6 packet.";
      }
      enum "pcep" {
        value 92;
        description 
          "Pcep packet.";
      }
      enum "radiusv6" {
        value 93;
        description 
          "Radiusv6 packet.";
      }
      enum "syslogv6" {
        value 94;
        description 
          "Syslogv6 packet.";
      }
      enum "vrrpv6" {
        value 95;
        description 
          "Vrrpv6 packet.";
      }
      enum "web-auth-serverv6" {
        value 96;
        description 
          "Web-auth-serverv6 packet.";
      }
      enum "cusp" {
        value 100;
        description 
          "Cusp packet.";
      }
    }
    description 
      "Protocol name.";
  }

  deviation "/cpudefend:cpudefend/cpudefend:policys/cpudefend:policy/cpudefend:enable" {
    deviate not-supported;
  }
  deviation "/cpudefend:cpudefend/cpudefend:policys/cpudefend:policy/cpudefend:user-defined-flow-car-enable" {
    deviate not-supported;
  }
  deviation "/cpudefend:cpudefend/cpudefend:policys/cpudefend:policy/cpudefend:alarm-protocol-names" {
    deviate not-supported;
  }
  deviation "/cpudefend:cpudefend/cpudefend:protocol-port-car" {
    deviate not-supported;
  }
  deviation "/cpudefend:cpudefend/cpudefend:urpf/cpudefend:global-urpf" {
    deviate not-supported;
  }
  deviation "/cpudefend:cpudefend/cpudefend:tm-scheduling/cpudefend:protocol-group-states/cpudefend:protocol-group-state/cpudefend:fq-states" {
    deviate not-supported;
  }
  deviation "/cpudefend:cpudefend/cpudefend:port-mac-filter" {
    deviate not-supported;
  }
  deviation "/cpudefend:reset-acl-statistics" {
    deviate not-supported;
  }
  deviation "/cpudefend:reset-rate-limit-statistics" {
    deviate not-supported;
  }
  deviation "/cpudefend:reset-port-car-rate-limit-statistics" {
    deviate not-supported;
  }
  deviation "/cpudefend:reset-port-mac-filter-statistics" {
    deviate not-supported;
  }
  deviation "/cpudefend:reset-cpcar-statistics" {
    deviate not-supported;
  }
  deviation "/devm:devm/devm:mpu-boards/devm:mpu-board/cpudefend:cpudefend" {
    deviate not-supported;
  }
  deviation "/devm:devm/devm:mpu-boards/devm:mpu-board/cpudefend:cpudefend-devm" {
    deviate not-supported;
  }
  deviation "/devm-vnf:devm-vnf/devm-vnf:vnf-boards/devm-vnf:vnf-board/cpudefend:cpudefend" {
    deviate not-supported;
  }
  deviation "/devm-vnf:devm-vnf/devm-vnf:vnf-boards/devm-vnf:vnf-board/cpudefend:cpudefend-devm" {
    deviate not-supported;
  }
  deviation "/ifm:ifm/ifm:interfaces/ifm:interface/cpudefend:cpudefend/cpudefend:protocol-port-car" {
    deviate not-supported;
  }
  deviation "/ifm:ifm/ifm:interfaces/ifm:interface/cpudefend:cpudefend/cpudefend:mac-filter" {
    deviate not-supported;
  }
  deviation "/cpudefend:cpudefend/cpudefend:policys/cpudefend:policy/cpudefend:cpcar-protocol-names/cpudefend:cpcar-protocol-name/cpudefend:protocol-name" {
    deviate replace {
      type cpudefend-devs-OC-NE-X8X16:protocol-name-deviations;
    }
  }
  deviation "/cpudefend:cpudefend/cpudefend:policys/cpudefend:policy/cpudefend:total-car/cpudefend:cpu-defend-total-car/cpudefend:rate-limit/cpudefend:value/cpudefend:value" {
    deviate replace {
      type uint32 {
        range "2000..50000";
      }
    }
  }
  deviation "/cpudefend:cpudefend/cpudefend:policys/cpudefend:policy/cpudefend:tm-scheduling/cpudefend:protocol-group-settings/cpudefend:protocol-group-setting/cpudefend:group" {
    deviate replace {
      type cpudefend-devs-OC-NE-X8X16:protocol-group-deviations;
    }
  }
  ext:deviation-ext "/cpudefend:cpudefend/cpudefend:policys/cpudefend:policy/cpudefend:tm-scheduling/cpudefend:protocol-group-settings/cpudefend:protocol-group-setting/cpudefend:weight" {
    ext:deviate-ext add {
      ext:dynamic-default  {
        ext:default-value "4" {
          when "../group = 'management' or ../group = 'multicast' or ../group = 'link-layer' or ../group = 'user-defined-flow' or ../group = 'route'";
          description "The default value is 4 when type is management or multicast or link-layer or user-defined-flow or route.";
        }
        ext:default-value "10" {
          when "../group = 'whitelist'";
          description "The default value is 10 when type is whitelist.";
        }
        ext:default-value "3" {
          when "../group = 'access-user' or ../group = 'network-layer'";
          description "The default value is 3 when type is access-user or network-layer.";
        }
        ext:default-value "2" {
          when "../group = 'mpls' or ../group = 'arp'";
          description "The default value is 2 when type is MPLS or ARP.";
        }
        ext:default-value "1" {
          when "../group = 'blacklist' or ../group = 'check-failed' or ../group = 'fwddata-to-cp' or ../group = 'system-message'";
          description "The default value is 1 when type is blacklist or check-failed or fwddata-to-cp or system-message.";
        }
      }
    }
  }
  deviation "/cpudefend:cpudefend/cpudefend:cpcar/cpudefend:protocol-name-statisticss/cpudefend:protocol-name-statistics/cpudefend:protocol-name" {
    deviate replace {
      type cpudefend-devs-OC-NE-X8X16:protocol-name-deviations;
    }
  }
  deviation "/cpudefend:cpudefend/cpudefend:cpcar/cpudefend:ap-protocol-name-statisticss/cpudefend:ap-protocol-name-statistics/cpudefend:protocol-name" {
    deviate replace {
      type cpudefend-devs-OC-NE-X8X16:protocol-name-deviations;
    }
  }
  deviation "/cpudefend:cpudefend/cpudefend:tm-scheduling/cpudefend:protocol-group-statisticss/cpudefend:protocol-group-statistics/cpudefend:group" {
    deviate replace {
      type cpudefend-devs-OC-NE-X8X16:protocol-group-deviations;
    }
  }
  deviation "/cpudefend:cpudefend/cpudefend:tm-scheduling/cpudefend:protocol-group-states/cpudefend:protocol-group-state/cpudefend:group" {
    deviate replace {
      type cpudefend-devs-OC-NE-X8X16:protocol-group-deviations;
    }
  }
  deviation "/cpudefend:reset-car-protocol-name-statistics/cpudefend:input/cpudefend:protocol-name" {
    deviate replace {
      type cpudefend-devs-OC-NE-X8X16:protocol-name-reset-deviations;
    }
  }
  deviation "/cpudefend:reset-car-protocol-name-ap-statistics/cpudefend:input/cpudefend:protocol-name" {
    deviate replace {
      type cpudefend-devs-OC-NE-X8X16:protocol-name-reset-deviations;
    }
  }
  deviation "/cpudefend:save-attack-source-trace/cpudefend:input/cpudefend:link-type" {
    deviate replace {
      type cpudefend-devs-OC-NE-X8X16:link-type-deviations;
    }
  }

}
