/*
Copyright (C) 2021 Huawei Technologies Co., Ltd. All rights reserved.
*/
module huawei-snmp-deviations-ATN-910C {
  namespace "urn:huawei:yang:huawei-snmp-deviations-ATN-910C";
  prefix snmp-devs-ATN-910C;

  import huawei-snmp {
    prefix snmp;
  }
  import huawei-aaa {
    prefix aaa;
  }

  organization
    "Huawei Technologies Co., Ltd.";
  contact
    "Huawei Industrial Base
     Bantian, Longgang
     Shenzhen 518129
     People's Republic of China
     Website: http://www.huawei.com
     Email: support@huawei.com";
  description
    "This module defines deviation statements for huawei-snmp module.";

  revision 2021-05-07 {
    description
      "Initial revision.";
    reference "Huawei private.";
  }

  deviation "/snmp:snmp/snmp:system/snmp:trap-source-ipv4-address" {
    deviate not-supported;
  }
  deviation "/snmp:snmp/snmp:target-hosts/snmp:target-host/snmp:is-need-heart-beat" {
    deviate not-supported;
  }
  deviation "/snmp:snmp/snmp:target-hosts/snmp:target-host/snmp:heart-beat-time" {
    deviate not-supported;
  }
  deviation "/snmp:snmp/snmp:target-hosts/snmp:target-host/snmp:status" {
    deviate not-supported;
  }
  deviation "/snmp:snmp/snmp:local-users/snmp:local-user/snmp:name" {
    deviate add {
      must "/aaa:aaa/aaa:lam/aaa:users/aaa:user[aaa:name = current()]/aaa:service-snmp = 'true'";
    }
  }
}
