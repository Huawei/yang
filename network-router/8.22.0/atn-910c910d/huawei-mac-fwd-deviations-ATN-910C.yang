/*
Copyright (C) 2019 Huawei Technologies Co., Ltd. All rights reserved.
*/
module huawei-mac-fwd-deviations-ATN-910C {
  namespace "urn:huawei:yang:huawei-mac-fwd-deviations-ATN-910C";
  prefix mac-fwd-devs-ATN-910C;

  import huawei-mac-fwd {
    prefix mac-fwd;
  }

  import huawei-devm {
    prefix devm;
  }

  import huawei-mac {
    prefix mac;
  }

  organization
    "Huawei Technologies Co., Ltd.";

  contact
    "Huawei Industrial Base
     Bantian, Longgang
     Shenzhen 518129
     People's Republic of China
     Website: http://www.huawei.com
     Email: support@huawei.com";

  description
    "This module defines deviation statements for huawei-mac-fwd module.";

  revision 2019-11-06 {
    description
      "Initial revision.";
    reference
      "Huawei private.";
  }

  deviation "/devm:devm/devm:lpu-boards/devm:lpu-board/mac-fwd:mac-sync" {
    deviate not-supported;
  }
  deviation "/mac:mac/mac:global-attribute/mac-fwd:mac-fwd" {
    deviate not-supported;
  }

}
