/*
Copyright (C) 2019-2022 Huawei Technologies Co., Ltd. All rights reserved.
*/
module huawei-bgp-vpnv4mcast {
  yang-version 1;
  namespace "urn:huawei:yang:huawei-bgp-vpnv4mcast";
  prefix bgp-vpnv4mcast;
  import huawei-extension {
    prefix ext;
  }
  import huawei-network-instance {
    prefix ni;
  }
  import huawei-bgp {
    prefix bgp;
  }
  import huawei-xpl {
    prefix xpl;
  }
  import huawei-routing-policy {
    prefix rtp;
  }
  import huawei-bgp-routing-table {
    prefix bgp-rt;
  }
  import ietf-inet-types {
    prefix inet;
  }
  import huawei-pub-type {
    prefix pub-type;
  }
  organization
    "Huawei Technologies Co., Ltd.";
  contact
    "Huawei Industrial Base
    Bantian, Longgang
    Shenzhen 518129
    People's Republic of China
    Website: http://www.huawei.com
    Email: support@huawei.com";
  description
    "Inter-AS routing protocol that exchanges Network Layer Reachability Information (NLRI) with other BGP systems.";
  revision 2022-08-23 {
    description
      "Add IPv4-vpn-multicast routing table of peer. Add IPv4-vpn-multicast route attributes.";
    reference "Huawei private.";
  }
  revision 2022-02-14 {
    description
      "Add IPv4-vpn-multicast routing table.";
    reference "Huawei private.";
  }
  revision 2020-08-30 {
    description
      "The YANG descriptions are modified according to new standards.";
    reference "Huawei private.";
  }
  revision 2019-03-22 {
    description
      "Initial revision.";
    reference
      "Huawei private.";
  }
  grouping routing-table-key-type {
    description
      "BGP routing-table attributes.";
    uses bgp-rt:routing-table-vpn-name;
    uses bgp-rt:routing-table-route-distinguisher;
    uses bgp-rt:routing-table-prefix;
    uses bgp-rt:routing-table-mask-length;
    uses bgp-rt:routing-table-route-type;
    uses bgp-rt:routing-table-im-table-id;
    uses bgp-rt:routing-table-from;
  }
  grouping routing-table-peer-address {
    description
      "BGP routing table peer address.";
    leaf remote-peer-address {
      type inet:ip-address-no-zone;
      description
        "BGP neighbor address.";
    }
  }
  grouping routing-table-prefix-peer {
    description
      "BGP routing table attributes.";
    leaf nexthop {
      type inet:ip-address-no-zone;
      description
        "Next hop address to which packets are forwarded.";
    }
    leaf flag-string {
      type string {
        length "1..100";
      }
      description
        "Route flag that contains a string of characters.";
    }
    leaf time {
      type pub-type:time-tick;
      description
        "Time stamp of a route.";
    }
    leaf interface-name {
      type string {
        length "1..63";
      }
      description
        "Name of the outbound interface of a route.";
    }
    leaf remote-route-id {
      type inet:ipv4-address-no-zone;
      description
        "Router ID of a peer.";
    }
    leaf relay-nexthop {
      type inet:ip-address-no-zone;
      description
        "Next hop to which a route is iterated.";
    }
    leaf relay-tunnel-name {
      type string {
        length "1..64";
      }
      description
        "Name of a tunnel to which a route is iterated.";
    }
  }
  grouping worse-reason {
    description
      "Reason why a route is not selected.";
    leaf worse-reason {
      type string {
        length "1..50";
      }
      description
        "Reason why a route is not selected.";
    }
  }
  grouping advertise-nexthop {
    description
      "Advertise nexthop.";
    leaf advertise-nexthop {
      type inet:ip-address-no-zone;
      description
        "Advertise nexthop.";
    }
  }
  grouping routing-table-prefix-type {
    description
      "BGP routing-table attributes.";
    uses routing-table-key-type;
    uses bgp-rt:routing-table-prefix-base-attr-type;
  }
  grouping attribute-index-type {
    description
      "The ID of attribute.";
    leaf attribute-index {
      type leafref {
        path "/bgp:bgp/bgp:base-process/bgp-rt:bgp-route/bgp-vpnv4mcast:ipv4-vpn-multicast/bgp-vpnv4mcast:attributes/bgp-vpnv4mcast:attribute/bgp-vpnv4mcast:index";
      }
      description
        "The ID of attribute.";
    }
  }
  grouping ipv4-vpn-multicast-routing-table {
    description
      "Information about routes.";
    container routes {
      description
        "List of displayed route information in an address family.";
      list route {
        key "vpn-name route-distinguisher prefix mask-length route-type im-table-id from";
        description
          "Operational data of route.";
        uses routing-table-prefix-type;
        uses bgp-rt:routing-public-attributes;
        uses attribute-index-type;
      }
    }
    container peer-advertise-routes {
      description
        "List of displayed advertised vpnv4mulcast route information in an address family.";
      list peer-advertise-route {
        key "vpn-name route-distinguisher prefix mask-length route-type im-table-id from remote-peer-address";
        description
          "Statistics of advertised vpnv4mulcast routes.";
        uses routing-table-key-type;
        uses routing-table-peer-address;
        uses routing-table-prefix-peer;
        uses advertise-nexthop;
        uses bgp-rt:routing-public-attributes;
        uses attribute-index-type;
      }
    }
    container peer-receive-routes {
      description
        "List of displayed received vpnv4mulcast route information in an address family.";
      list peer-receive-route {
        key "vpn-name route-distinguisher prefix mask-length route-type im-table-id from remote-peer-address";
        description
          "Statistics of received vpnv4mulcast routes.";
        uses routing-table-key-type;
        uses routing-table-peer-address;
        uses routing-table-prefix-peer;
        uses worse-reason;
        uses bgp-rt:routing-public-attributes;
        uses attribute-index-type;
      }
    }
  }
  ext:task-name "bgp";
  augment "/ni:network-instance/ni:instances/ni:instance/bgp:bgp/bgp:base-process/bgp:afs/bgp:af" {
    description
      "BGP IPv4 vpnv4-multicast address family configuration.";
    container ipv4-vpn-multicast {
      when "../bgp:type='ipv4vpnmcast'";
      description
        "Configure IPv4 vpnv4-multicast address family.";
      container common {
        description
          "Configure BGP IPv4 vpnv4-multicast common options.";
        uses bgp:vpn-target-type;
        uses bgp:reflector-cluster-type;
        leaf reflect-between-client {
          type boolean;
          default "true";
          description
          "Enable/disable route reflection between clients.";
        }
        leaf reflect-change-path {
          type boolean;
          default "false";
          description
            "Enable/disable an RR to use an export policy to change route AS_Path. By default, this function is not enabled.";
        }
      }
      uses bgp:slow-peer-type;
    }
  }
  augment "/ni:network-instance/ni:instances/ni:instance/bgp:bgp/bgp:base-process/bgp:peer-groups/bgp:peer-group/bgp:afs/bgp:af" {
    description
      "BGP IPv4 vpnv4-multicast address family configuration.";
    container ipv4-vpn-multicast {
      when "../bgp:type='ipv4vpnmcast'";
      description
        "Configure BGP IPv4 vpnv4-multicast options.";
      uses bgp:rt-update-interval-type;
      uses bgp:advertise-large-community-group-type;
      uses bgp:advertise-community-type;
      uses bgp:group-independent-peer-group-type;
      leaf reflect-client {
        when "../../../../bgp:type='ibgp'";
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/rtp:routing-policy/rtp:policy-definitions/rtp:policy-definition/rtp:name";
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/xpl:xpl/xpl:route-filters/xpl:route-filter/xpl:name";
              }
              description
                "Specify an import route-filter name.";
            }
            leaf parameter {
              when "../name";
              type xpl:filter-parameter-type;
              description
                "Specify an import route-filter parameter.";
            }
          }
        }
      }
      choice export-policy-type {
        description
          "Set route policy or filter.";
        case rtp-ref {
          description
            "Route policy.";
          leaf export-policy {
            type leafref {
              path "/rtp:routing-policy/rtp:policy-definitions/rtp:policy-definition/rtp:name";
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/xpl:xpl/xpl:route-filters/xpl:route-filter/xpl:name";
              }
              description
                "Specify an export route-filter name.";
            }
            leaf parameter {
              when "../name";
              type xpl:filter-parameter-type;
              description
                "Specify an export route-filter parameter.";
            }
          }
        }
      }
      leaf update-packet-standard-compatible {
        type boolean;
        default "false";
        description
          "Enable/disable compatible standard update packet.";
      }
      uses bgp:route-limit-type;
    }
  }
  augment "/ni:network-instance/ni:instances/ni:instance/bgp:bgp/bgp:base-process/bgp:peers/bgp:peer/bgp:afs/bgp:af" {
    description
      "BGP IPv4 vpnv4-multicast address family configuration.";
    container ipv4-vpn-multicast {
      when "../bgp:type = 'ipv4vpnmcast'";
      description
        "Configure IPv4 vpnv4-multicast options.";
      leaf group-name {
        type leafref {
          path "../../../../../../bgp:peer-groups/bgp:peer-group/bgp:name";
        }
        must "../../../../../../bgp:peer-groups/bgp:peer-group[bgp:name = current()]/bgp:afs/bgp:af[bgp:type='ipv4vpnmcast']";
        must "../../../../../../bgp:peer-groups/bgp:peer-group[bgp:name = current()]/bgp:peer-establish-mode = 'static'";
        description
          "Configure a name for a peer group. After a peer is deleted from the peer group, the peer is disabled from the address family. The object cannot be modified.";
        ext:operation-exclude update {
          description "The node cannot be modified, when the peer already belongs to a peer-group.";
        }
      }
      uses bgp:rt-update-interval-type;
      uses bgp:advertise-large-community-type;
      uses bgp:advertise-community-type;
      uses bgp:peer-independent-peer-group-type;
      leaf reflect-client {
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/rtp:routing-policy/rtp:policy-definitions/rtp:policy-definition/rtp:name";
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/xpl:xpl/xpl:route-filters/xpl:route-filter/xpl:name";
              }
              description
                "Specify an import route-filter name.";
            }
            leaf parameter {
              when "../name";
              type xpl:filter-parameter-type;
              description
                "Specify an import route-filter parameter.";
            }
          }
        }
      }
      choice export-policy-type {
        description
          "Set route policy or filter.";
        case rtp-ref {
          description
            "Route policy.";
          leaf export-policy {
            type leafref {
              path "/rtp:routing-policy/rtp:policy-definitions/rtp:policy-definition/rtp:name";
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/xpl:xpl/xpl:route-filters/xpl:route-filter/xpl:name";
              }
              description
                "Specify an export route-filter name.";
            }
            leaf parameter {
              when "../name";
              type xpl:filter-parameter-type;
              description
                "Specify an export route-filter parameter.";
            }
          }
        }
      }
      leaf update-packet-standard-compatible {
        type boolean;
        default "false";
        description
          "Enable/disable compatible standard update packet.";
      }
      uses bgp:route-limit-type;
      uses bgp:path-attr-map-type;
    }
  }
  augment "/bgp:bgp/bgp:base-process/bgp-rt:bgp-route" {
    description
      "BGP IPv4 vpnv4-multicast address family routes information.";
    container ipv4-vpn-multicast {
      config false;
      description
        "Statistics of IPv4 vpnv4-multicast routes.";
      uses ipv4-vpn-multicast-routing-table;
      uses bgp-rt:route-attribute-info-ext;
      container statistic {
        description
          "Statistics of BGP routes information of IPv4 vpnv4-multicast address family.";
        uses bgp-rt:route-total-st-type;
      }
    }
  }
}
