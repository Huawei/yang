/*
Copyright (C) 2021 Huawei Technologies Co., Ltd. All rights reserved.
*/
module huawei-openconfig-bfd-deviations-ATN-910C {
  namespace "urn:huawei:yang:huawei-openconfig-bfd-deviations-ATN-910C";
  prefix oc-bfd-devs-ATN-910C;

  import openconfig-bfd {
    prefix oc-bfd;
  }

  organization
    "Huawei Technologies Co., Ltd.";
  contact
    "Huawei Industrial Base
     Bantian, Longgang
     Shenzhen 518129
     People's Republic of China
     Website: http://www.huawei.com
     Email: support@huawei.com";
  description
    "This module defines deviation statements for openconfig-bfd module.";

  revision 2021-05-07 {
    description
      "Initial revision.";
    reference "Huawei private.";
  }

  deviation "/oc-bfd:bfd" {
    deviate not-supported;
  }
}
