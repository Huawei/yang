/*
Copyright (C) 2021 Huawei Technologies Co., Ltd. All rights reserved.
*/
module huawei-mpls-forward-deviations-ATN-910C {
  namespace "urn:huawei:yang:huawei-mpls-forward-deviations-ATN-910C";
  prefix mpls-forward-devs-ATN-910C;

  import huawei-mpls-forward {
    prefix mpls-forward;
  }

  import huawei-ifm {
    prefix ifm;
  }

  import huawei-mpls-te {
    prefix mpls-te;
  }

  import huawei-mpls {
    prefix mpls;
  }

  import huawei-tunnel-management {
    prefix tnlm;
  }

  organization
    "Huawei Technologies Co., Ltd.";

  contact
    "Huawei Industrial Base
     Bantian, Longgang
     Shenzhen 518129
     People's Republic of China
     Website: http://www.huawei.com
     Email: support@huawei.com";

  description
    "This module defines deviation statements for huawei-mpls-forward module.";

  revision 2021-05-07 {
    description
      "Initial revision.";
    reference
      "Huawei private.";
  }

  deviation "/ifm:ifm/ifm:interfaces/ifm:interface/mpls-forward:bgp-localifnet-traffic" {
    deviate not-supported;
  }
  deviation "/ifm:ifm/ifm:interfaces/ifm:interface/tnlm:tunnel-protocol/tnlm:type/mpls-te:mpls-te/mpls-te:te-tunnel/mpls-forward:mplstunnelpipe/mpls-forward:color" {
    deviate not-supported;
  }
  deviation "/mpls:mpls/mpls-forward:p2mp-fastswitch" {
    deviate not-supported;
  }
  deviation "/mpls:mpls/mpls-forward:te-reverse-path-forwarding/mpls-forward:te-rpf-enable" {
    deviate replace {
      default "disable";
    }
  }

}
