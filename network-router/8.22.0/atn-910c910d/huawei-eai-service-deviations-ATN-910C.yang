/*
Copyright (C) 2021 Huawei Technologies Co., Ltd. All rights reserved.
*/
module huawei-eai-service-deviations-ATN-910C {
  namespace "urn:huawei:yang:huawei-eai-service-deviations-ATN-910C";
  prefix eai-service-devs-ATN-910C;

  import huawei-eai-service {
    prefix eai-service;
  }

  organization
    "Huawei Technologies Co., Ltd.";

  contact
    "Huawei Industrial Base
     Bantian, Longgang
     Shenzhen 518129
     People's Republic of China
     Website: http://www.huawei.com
     Email: support@huawei.com";

  description
    "This module defines deviation statements for huawei-eai-service module.";

  revision 2021-05-07 {
    description
      "Initial revision.";
    reference
      "Huawei private.";
  }

  deviation "/eai-service:eai-service/eai-service:global/eai-service:anomaly-detection-enable" {
    deviate not-supported;
  }

}
