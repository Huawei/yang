/*
Copyright (C) 2021 Huawei Technologies Co., Ltd. All rights reserved.
*/
module huawei-bfd-static-vpws-deviations-ATN-910C {
  namespace "urn:huawei:yang:huawei-bfd-static-vpws-deviations-ATN-910C";
  prefix bfd-static-vpws-devs-ATN-910C;

  import huawei-bfd-static-vpws {
    prefix bfd-static-vpws;
  }
  import huawei-bfd {
    prefix bfd;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd-static-vpws module.";

  revision 2021-05-07 {
    description
      "Initial revision.";
    reference "Huawei private.";
  }

  deviation "/bfd:bfd/bfd:sessions/bfd:session/bfd:session-type/bfd:static/bfd:static-session-link-type/bfd-static-vpws:vll-pw/bfd-static-vpws:select-board-slot-static-vll-pw" {
    deviate not-supported;
  }
  deviation "/bfd:bfd/bfd:sessions/bfd:session/bfd-static-vpws:vpws-groups" {
    deviate not-supported;
  }
  deviation "/bfd:bfd/bfd:sessions/bfd:session/bfd:session-type/bfd:static/bfd:static-session-link-type/bfd-static-vpws:vll-pw/bfd-static-vpws:is-group-static-vll-pw" {
    deviate delete {
      must "../is-group-static-vll-pw='false' or not(../select-board-slot-static-vll-pw)";
    }
    deviate add {
      must "../bfd-static-vpws:is-group-static-vll-pw='false'";
    }
  }
}
