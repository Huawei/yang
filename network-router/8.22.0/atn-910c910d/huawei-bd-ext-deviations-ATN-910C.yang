/*
Copyright (C) 2021 Huawei Technologies Co., Ltd. All rights reserved.
*/
module huawei-bd-ext-deviations-ATN-910C {
  namespace "urn:huawei:yang:huawei-bd-ext-deviations-ATN-910C";
  prefix bd-ext-devs-ATN-910C;

  import huawei-bd-ext {
    prefix bd-ext;
  }

  import huawei-bd {
    prefix bd;
  }

  organization
    "Huawei Technologies Co., Ltd.";

  contact
    "Huawei Industrial Base
     Bantian, Longgang
     Shenzhen 518129
     People's Republic of China
     Website: http://www.huawei.com
     Email: support@huawei.com";

  description
    "This module defines deviation statements for huawei-bd-ext module.";

  revision 2021-05-07 {
    description
      "Initial revision.";
    reference
      "Huawei private.";
  }

  deviation "/bd:bd/bd:instances/bd:instance/bd-ext:pipe" {
    deviate not-supported;
  }
  deviation "/bd:bd/bd:instances/bd:instance/bd-ext:reserve-if-switch" {
    deviate not-supported;
  }

}
