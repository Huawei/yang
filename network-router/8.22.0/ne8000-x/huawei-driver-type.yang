/*
Copyright (C) 2020-2021 Huawei Technologies Co., Ltd. All rights reserved.
*/
submodule huawei-driver-type {
  belongs-to huawei-driver {
    prefix driver;
  }
  
  organization
    "Huawei Technologies Co., Ltd.";
  contact
    "Huawei Industrial Base
     Bantian, Longgang
     Shenzhen 518129
     People's Republic of China
     Website: http://www.huawei.com
     Email: support@huawei.com";
  description
    "Description of driver type.";
  revision 2021-12-10 {
    description
      "Add types about driver-hardware-version-type.";
    reference
      "Huawei private.";
  }
  revision 2021-12-01 {
    description
      "Add types about driver-hardware-version-type.";
    reference
      "Huawei private.";
  }
  revision 2021-11-08 {
    description
      "Add types about power redundant mode.";
    reference
      "Huawei private.";
 }
  revision 2021-04-09 {
    description
      "Add types about ap.";
    reference
      "Huawei private.";
  }
  revision 2021-03-02 {
    description
      "Add types about LED indicators.";
    reference
      "Huawei private.";
  }
  revision 2020-03-25 {
    description
      "Init revision.";
    reference
      "Huawei private.";
  }
  
  typedef driver-link-chassis-type {
    type enumeration {
      enum "other" {
        value 0;
        description
          "Other.";
      }
      enum "central-chassis" {
        value 1;
        description
          "Cluster central chassis.";
      }
      enum "line-chassis" {
        value 2;
        description
          "Cluster line chassis.";
      }
    }
    description
      "Driver-link-chassis-type.";
  }
    typedef driver-item-type {
    type enumeration {
      enum "bios" {
        value 0;
        description
          "Bios.";
      }
      enum "bootload" {
        value 1;
        description
          "Bootload.";
      }
    }
    description
      "Driver-item-type.";
  }
   typedef driver-result-type {
    type enumeration {
      enum "fail" {
        value 0;
        description
          "FAIL.";
      }
      enum "pass" {
        value 1;
        description
          "PASS.";
      }
	  enum "not-support" {
        value 2;
        description
          "NOT SUPPORT.";
      }
    }
    description
      "Driver-result-type.";
  }
  typedef driver-inner-link-type {
    type enumeration {
      enum "other" {
        value 0;
        description
          "Other.";
      }
      enum "control-channel" {
        value 1;
        description
          "Control Channel.";
      }
      enum "monitor-channel" {
        value 2;
        description
          "Monitor Channel.";
      }
      enum "forward-channel" {
        value 3;
        description
          "Forward Channel.";
      }
    }
    description
      "Information of enum type.";
  }

  typedef driver-link-state-type {
    type enumeration {
      enum "normal" {
        value 0;
        description
          "Normal.";
      }
      enum "partial-fault" {
        value 1;
        description
          "Partial Fault.";
      }
      enum "fault" {
        value 2;
        description
          "Fault.";
      }
    }
    description
      "Information of enum type driver-link-state-type.";
  }

  typedef driver-bool {
    type enumeration {
      enum "yes" {
        value 1; 
        description
          "YES.";
      }
      enum "no" {
        value 0;
        description
          "NO.";
      }
    }
    description
      "Information of enum type driver-bool.";
  }
  typedef driver-entity-bool {
    type enumeration {
      enum "enable" {
        value 1; 
        description
          "Enable.";
      }
      enum "disable" {
        value 0;
        description
          "Disable.";
      }
    }
    description
      "Information of enum type driver-entity-bool.";
  }
  typedef driver-power-work-mode {
    type enumeration {
      enum "DC" {
        value 1;
        description
          "DC.";
      }
      enum "AC" {
        value 2;
        description
          "AC.";
      }
      enum "HVDC" {
        value 3;
        description
          "HVDC.";
      }
      enum "unknown" {
        value 4;
        description
          "UNKNOWN.";
      }
    }
    description
      "Information of enum type driver-power-work-mode.";
  }

  typedef driver-cable-state {
    type enumeration {
      enum "plug" {
        value 1;
        description
          "Plug.";
      }
      enum "un-plug" {
        value 0;
        description
          "Unplug.";
      }
    }
    description
      "Information of enum type driver-cable-state.";
  }
  typedef driver-pm-status {
    type enumeration {
      enum "abnormal" {
        value 1;
        description
          "Abnormal.";
      }
      enum "normal" {
        value 0;
        description
          "Normal.";
      }
    }
    description
      "Information of enum type pm status.";
  }
  typedef driver-dacs-status {
    type enumeration {
      enum "abnormal" {
        value 1;
        description
          "Abnormal.";
      }
      enum "normal" {
        value 0;
        description
          "Normal.";
      }
    }
    description
      "Information of enum type dacs status.";
  }
 
  typedef driver-clock-status {
    type enumeration {
      enum "normal" {
        value 1;
        description
          "Normal.";
      }
      enum "abnormal" {
        value 0;
        description
          "Abnormal.";
      }
    }
    description
      "Information of enum type clock status.";
  }
  
  typedef driver-sensor-state {
    type enumeration {
      enum "unknown" {
        value 4;
        description
          "Unknown.";
      }
      enum "normal" {
        value 0;
        description
          "Normal state.";
      }
      enum "minor" {
        value 1;
        description
          "Minor alarm.";
      }
      enum "major" {
        value 2;
        description
          "Major alarm.";
      }
      enum "fatal" {
        value 3;
        description
          "Fatal alarm.";
      }
      enum "unsupported" {
        value 5;
        description
          "Unsupported.";
      }
    }
    description
      "Information of enum type driver-sensor-state.";
  }
  
  typedef driver-system-mode {
    type enumeration {
      enum "redundant" {
        value 1;
        description
          "Redundant mode.";
      }
      enum "non-redundant" {
        value 2;
        description
          "Non-redundant mode.";
      }
    }
    description
      "Information of enum type driver-system-mode.";
  }

  typedef driver-switch-alarm-triggering-mode {
    type enumeration {
      enum "falling-edge" {
        value 0;
        description
          "Alarm when switch turn to 0.";
      }
      enum "rising-edge" {
        value 1;
        description
          "Alarm when switch turn to 1.";
      }
    }
    description
      "Information of enum type driver-switch-alarm-triggering-mode.";
  }
  typedef driver-relay-mode {
    type enumeration {
      enum "open" {
        value 0;
        description
          "Turns on an external device through an external relay.";
      }
      enum "close" {
        value 1;
        description
          "Turns off an external device through an external relay.";
      }
    }
    description
      "Information of enum type driver-relay-mode.";
  }
  typedef driver-sensor-name {
    type enumeration {
      enum "fog" {
        value 1;
        description
          "Fog sensor.";
      }
    }
    description
      "Information of enum type driver-sensor-name.";
  }
  
  typedef driver-analog-type {
    type enumeration {
      enum "current" {
        value 1;
        description
          "Specifies a current sensor.";
      }
      enum "voltage" {
        value 2;
        description
          "Specifies a voltage sensor.";
      }
    }
    description
      "Information of enum type driver-analog-type.";
  }
  typedef driver-analog-object-type {
    type enumeration {
      enum "temperature" {
        value 2;
        description
          "Monitors the temperature.";
      }
      enum "humidity" {
        value 3;
        description
          "Monitors the humidity.";
      }
    }
    description
      "Information of enum type driver-analog-object-type.";
  }
  
  typedef energy-mode-type {
    type enumeration {
      enum "basic" {
        value 0;
        description
          "Basic.";
      }
      enum "standard" {
        value 1;
        description
          "Standard.";
      }
      enum "deep" {
        value 2;
        description
          "Deep.";
      }
      enum "optimal" {
        value 3;
        description
          "Optimal.";
      }
      enum "not-support" {
        value 4;
        description
          "Not support.";
      }
    }
    description
      "Information of enum type energy-mode-type.";
  }
  typedef driver-online-status-type {
    type enumeration {
      enum "absent" {
        value 0;
        description
          "Absent.";
      }
      enum "present" {
        value 1;
        description
          "Present.";
      }
      enum "offline" {
        value 2;
        description
          "Offline.";
      }
      enum "unknown" {
        value 3;
        description
          "Unknown.";
      }
    }
    description
      "Information of enum type online-status.";
  }
  typedef driver-register-status-type {
    type enumeration {
      enum "unregistered" {
        value 0;
        description
          "Unregistered.";
      }
      enum "registered" {
        value 1;
        description
          "Registered.";
      }
      enum "NA" {
        value 2;
        description
          "NA.";
      }
    }
    description
      "Information of enum type register-status.";
  }
  typedef driver-running-status-type {
    type enumeration {
      enum "abnormal" {
        value 0;
        description
          "Abnormal.";
      }
      enum "normal" {
        value 1;
        description
          "Normal.";
      }
      enum "isolated" {
        value 2;
        description
          "Isolated.";
      }
      enum "not-install" {
        value 3;
        description
          "Not install.";
      }
      enum "wrong-type" {
        value 4;
        description
          "Wrong type.";
      }
      enum "NA" {
        value 9;
        description
          "NA.";
      }
    }
    description
      "Information of enum type running-status.";
  }
  typedef driver-role-type {
    type enumeration {
      enum "MMB" {
        value 1;
        description
          "MMB.";
      }
      enum "PLMB" {
        value 2;
        description
          "PLMB.";
      }
      enum "MB" {
        value 4;
        description
          "MB.";
      }
      enum "LC" {
        value 5;
        description
          "LC.";
      }
      enum "NET" {
        value 6;
        description
          "NET.";
      }
      enum "ICU" {
        value 7;
        description
          "ICU.";
      }
      enum "ECU" {
        value 8;
        description
          "ECU.";
      }
      enum "OTHER" {
        value 200;
        description
          "OTHER.";
      }
      enum "NA" {
        value 255;
        description
          "NA.";
      }
    }
    description
      "Role type.";
  }
  typedef driver-primary-status-type {
    type enumeration {
      enum "master" {
        value 0;
        description
          "Master.";
      }
      enum "slave" {
        value 1;
        description
          "Slave.";
      }
      enum "NA" {
        value 2;
        description
          "NA.";
      }
      enum "system-master" {
        value 3;
        description
          "System Master.";
      }
      enum "system-slave" {
        value 4;
        description
          "System Slave.";
      }
    }
    description
      "Information of enum type primary-status.";
  }
  typedef sfu-mode-type {
    type enumeration {
      enum "four-sfu" {
        value 1;
        description
          "Four-SFU mode.";
      }
      enum "six-sfu" {
        value 2;
        description
          "Six-SFU mode.";
      }
    }
    description
      "Information of enum type sfu-mode-type.";
  }
  typedef energy-saving-pm-type {
    type enumeration {
      enum "disable" {
        value 0;
        description
          "Disable.";
      }
      enum "enable" {
        value 1;
        description
          "Enable.";
      }
    }
    description
      "Information of enum type energy-saving-pm-type.";
  }
  typedef offline-function-type {
    type enumeration {
      enum "disable" {
        value 1;
        description
          "Disable.";
      }
      enum "enable" {
        value 0;
        description
          "Enable.";
      }
    }
    description
      "Information of enum type offline-function-type.";
  }
  typedef mib-query-mode-type {
    type enumeration {
      enum "default" {
        value 0;
        description
          "NO.";
      }
      enum "brief" {
        value 1;
        description
          "YES.";
      }
    }
    description
      "Information of enum type mib-query-mode-type.";
  }
  typedef pwr-supply-mode-type {
    type enumeration {
      enum "standard" {
        value 1;
        description
          "Standard.";
      }
      enum "assign" {
        value 2;
        description
          "Assign.";
      }
    }
    description
      "Information of enum type pwr-supply-mode-type.";
  }

  typedef pwr-redundant-mode-type {
    type enumeration {
      enum "non" {
        value 1;
        description
          "N+0 redundant.";
      }
      enum "module" {
        value 2;
        description
          "N+1 redundant.";
      }
      enum "source" {
        value 3;
        description
          "N+N redundant.";
      }
    }
    description
      "Information of enum type pwr-redundant-mode-type.";
  }

  typedef pwr-supply-temp-type {
    type enumeration {
      enum "templow" {
        value 40;
        description
          "40.";
      }
      enum "temphigh" {
        value 55;
        description
          "55.";
      }
      enum "tempmiddle" {
        value 50;
        description
          "50.";
      }
    }
    description
      "Information of enum type pwr-supply-temp-type.";
  }
  typedef warm-backup-mode {
    type enumeration {
      enum "disable" {
        value 0;
        description
          "Undo warm-backup mode enable.";
      }
      enum "enable" {
        value 1;
        description
          "Warm-backup mode enable.";
      }
    }
    description
      "Information of enum type warm-backup-mode.";
  }
  typedef entity-fault-isolate-type {
    type enumeration {
      enum "disable" {
        value 0;
        description
          "Undo entFaultIso enable.";
      }
      enum "enable" {
        value 1;
        description
          "EntFaultIso enable.";
      }
    }
    description
      "Information of enum type entity-fault-isolate-type.";
  }
  typedef sampling-period-type {
    type enumeration {
      enum "fifteen-minutes" {
        value 1;
        description
          "Fifteen minutes.";
      }
      enum "thirty-minutes" {
        value 2;
        description
          "Thirty minutes.";
      }
      enum "one-hour" {
        value 3;
        description
          "One hour.";
      }
      enum "one-day" {
        value 4;
        description
          "One day.";
      }
      enum "one-week" {
        value 5;
        description
          "One week.";
      }
      enum "one-month" {
        value 6;
        description
          "One month.";
      }
    }
    description
      "Power sampling period.";
  }
  typedef warm-backup-status {
    type enumeration {
      enum "off" {
        value 0;
        description
          "Warm-backup status : off.";
      }
      enum "on" {
        value 1;
        description
          "Warm-backup status : on.";
      }
    }
    description
      "Information of enum type warm-backup-status.";
  }

  typedef driver-vsu-service-type {
    type enumeration {
      enum "cgn" {
        value 1;
        description
          "Cgn.";
      }
      enum "qoe" {
        value 3;
        description
          "Qoe.";
      }
    }
    description
      "Information of enum type driver-vsu-service-type.";
  }
  typedef led-status-type {
    type enumeration {
      enum "dim" {
        value 0;
        description
          "LED dim.";
      }
      enum "red-light" {
        value 1;
        description
          "Red light.";
      }
      enum "green-light" {
        value 2;
        description
          "Green light.";
      }
      enum "green-blink" {
        value 3;
        description
          "Green blink.";
      }
    }
    description
      "Led status.";
  }
  typedef device-type {
    type enumeration {
      enum "usb-disk" {
        value 0;
        description
          "USB disk.";
      }
    }
    description
      "Device type of LED.";
  }
  typedef driver-interface-match-check-object {
    type enumeration {
      enum "card" {
        value 2;
        description
          "Card.";
      }
      enum "board" {
        value 1;
        description
          "Board.";
      }
    }
    description
      "Driver-interface-match-check-object.";
  }
  typedef driver-interface-match-check-flag {
    type enumeration {
      enum "enable" {
        value 1;
        description
          "Enable.";
      }
      enum "disable" {
        value 0;
        description
          "Disable.";
      }
    }
    description
      "Driver-interface-match-check-flag.";
  }

  typedef sfu-switch-mode-type {
    type enumeration {
      enum "enable" {
        value 1;
        description
          "Enable.";
      }
      enum "disable" {
        value 0;
        description
          "Disable.";
      }
    }
    description
      "Sfu-switch-mode-type.";
  }
  typedef driver-split-resume-mode-type {
    type enumeration {
      enum "slave-reset" {
        value 1;
        description
          "Slave-reset.";
      }
      enum "fast-preemption" {
        value 2;
        description
          "Fast-preemption.";
      }
    }
    description
      "Driver-split-resume-mode-type.";
  }
  typedef driver-multi-chassis-type {
    type enumeration {
      enum "ccc" {
        value 0;
        description
          "Ccc.";
      }
      enum "clc" {
        value 1;
        description
          "Clc.";
      }
    }
    description
      "Driver-multi-chassis-type.";
  }
  typedef driver-run-mode-type {
    type enumeration {
      enum "single" {
        value 1;
        description
          "Single.";
      }
      enum "ccc-0" {
        value 2;
        description
          "Ccc-0.";
      }
      enum "ccc-1" {
        value 3;
        description
          "Ccc-1.";
      }
      enum "ccc-2" {
        value 4;
        description
          "Ccc-2.";
      }
      enum "virtual-cluster-chassis" {
        value 6;
        description
          "Virtual-cluster-chassis.";
      }
    }
    description
      "Information of enum type driver-run-mode-type.";
  }

  typedef driver-single-input-type {
    type enumeration {
      enum "A" {
        value 1;
        description
          "Single Input Plane A.";
      }
      enum "B" {
        value 2;
        description
          "Single Input Plane B.";
      }
      enum "NA" {
        value 0;
        description
          "Undo Single Input.";
      }
    }
    description
      "Information of enum type driver-single-input-type.";
  }

  typedef rollback-choice-type {
    type enumeration {
      enum "no" {
        value 0;
        description
          "No.";
      }
      enum "yes" {
        value 1;
        description
          "Yes.";
      }
    }
    description
      "Information of enum type rollback-choice-type.";
  }

  typedef global-card-fault-process-mode {
    type enumeration {
      enum "reset" {
        value 0;
        description
          "Reset.";
      }
      enum "isolate" {
        value 1;
        description
          "Isolate.";
      }
    }
    description
      "Global-card-fault-process-mode.";
  }

  typedef driver-slot-infos-type {
    type enumeration {
      enum "MPU" {
        value 4159;
        description
          "MPU.";
      }
      enum "LPU" {
        value 4160;
        description
          "LPU.";
      }
      enum "SFU" {
        value 4161;
        description
          "SFU.";
      }
      enum "ICU" {
        value 4111;
        description
          "ICU.";
      }
      enum "PMU" {
        value 5031;
        description
          "PMU.";
      }
      enum "CMU" {
        value 5009;
        description
          "CMU.";
      }
      enum "FAN" {
        value 4163;
        description
          "FAN.";
      }
      enum "POWER" {
        value 4164;
        description
          "POWER.";
      }
      enum "IPU" {
        value 10248;
        description
          "IPU.";
      }
    }
    description
      "Driver-slot-infos-type.";
  }
  
  typedef driver-system-mode-type {
    type enumeration {
      enum "classic" {
        value 0;
        description
          "Classic.";
      }
      enum "ls" {
        value 1;
        description
          "Ls.";
      }
    }
    description
      "Driver-system-mode-type.";
  }
  typedef system-work-mode-type {
    type enumeration {
      enum "p-series" {
        value 0;
        description
          "The system work mode is p-series.";
      }
      enum "x-series" {
        value 1;
        description
          "The system work mode is x-series.";
      }
      enum "e-series" {
        value 2;
        description
          "The system work mode is e-series.";
      }
    }
    description
      "Information of enum type system-work-mode-type.";
  }
  typedef driver-upgrade-mode-type {
    type enumeration {
      enum "close" {
        value 1;
        description
          "Close.";
      }
      enum "open" {
        value 0;
        description
          "Open.";
      }
    }
    description
      "Driver-upgrade-mode-type.";
  } 
  typedef driver-flash-lock {
    type enumeration {
      enum "immediately" {
        value 0;
        description
          "Immediately.";
      }
      enum "delay" {
        value 1;
        description
          "Delay.";
      }
    }
    description
      "Driver-flash-lock.";
  }
  typedef driver-work-mode {
    type enumeration {
      enum "base-function" {
        value 0;
        description
          "Base Function.";
      }
      enum "ptn-iot-mode" {
        value 1;
        description
          "PTN IOT Mode.";
      }
    }
    description
      "Information of enum type driver-work-mode.";
  }
  typedef driver-usb-uart {
    type enumeration {
      enum "open" {
        value 6;
        description
          "Open.";
      }
      enum "close" {
        value 5;
        description
          "Close.";
      }
    }
    description
      "Information of enum driver-usb-uart.";
  }
  typedef usb-uart-status {
    type enumeration {
      enum "open" {
        value 0;
        description
          "Open.";
      }
      enum "closed" {
        value 1;
        description
          "Closed.";
      }
      enum "not-support" {
        value 2;
        description
          "Not-support.";
      }
    }
    description
      "Information of enum usb-uart-status.";
  }
  typedef driver-cmu-role {
    type enumeration {
      enum "master" {
        value 0;
        description
          "Master.";
      }
      enum "slave" {
        value 1;
        description
          "Slave.";
      }
	   enum "NA" {
        value 2;
        description
          "NA.";
      }
    }
    description
      "Driver-cmu-role.";
  } 
  typedef trap-type {
    type enumeration {
      enum "base-trap" {
        value 1;
        description
          "Base-trap.";
      }
      enum "dc-trap" {
        value 2;
        description
          "Dc-trap.";
      }
      enum "entity-trap" {
        value 4;
        description
          "Entity-trap.";
      }
    }
    description
      "Information of enum type trap-type.";
  }
  
  typedef forwarding-mode {
    type enumeration {
      enum "compatible" {
        value 1;
        description
          "Compatible.";
      }
      enum "enhance" {
        value 2;
        description
          "Enhance.";
      }
    }
    description
      "Information of enum type forwarding-mode.";
  }
  
  typedef fan-workmode {
    type enumeration {
      enum "auto" {
        value 1;
        description
          "Automatic.";
      }
      enum "manual" {
        value 2;
        description
          "Percent.";
      }
      enum "silent" {
        value 4;
        description
          "Silent.";
      }
      enum "full" {
        value 5;
        description
          "Full.";
      }
      enum "anti-corrosive-mode" {
        value 8;
        description 
          "Anti-corrosive-mode.";
      }
      enum "minimum-percent" {
        value 9;
        description
          "Minimum-percent.";
      }
      enum "denoise" {
        value 11;
        description
          "Denoise.";
      }
    }
    description
      "Information of enum type fan-workmode.";
  }
  
  typedef dustproof-gate-state {
    type enumeration {
      enum "enable" {
        value 0;
        description
          "Enable.";
      }
      enum "disable" {
        value 1;
        description
          "Disable.";
      }
    }
    description
      "Information of enum type dustproof-gate-state.";
  }
  
  typedef reload-time {
    type enumeration {
      enum "5min" {
        value 5;
        description
          "5min.";
      }
      enum "15min" {
        value 15;
        description
          "15min.";
      }
      enum "30min" {
        value 30;
        description
          "30min.";
      }
      enum "60min" {
        value 60;
        description
          "60min.";
      }
      enum "1440min" {
        value 1440;
        description
          "1440min.";
      }
    }
    description
      "Information of enum type reload-time.";
  }
  
  typedef driver-inspect-state {
    type enumeration {
      enum "close" {
        value 0;
        description
          "Close.";
      }
      enum "open" {
        value 1;
        description
          "Open.";
      }
      enum "NA" {
        value 2;
        description
          "NA.";
      }
    }
    description
      "Information of enum type driver-inspect-state.";
  }
  
  typedef driver-inspect-alarm-state {
    type enumeration {
      enum "abnormal" {
        value 0;
        description
          "Abnormal.";
      }
      enum "normal" {
        value 1;
        description
          "Normal.";
      }
    }
    description
      "Information of enum type driver-inspect-alarm-state.";
  }
  
  typedef driver-auto-upgrade-mode {
    type enumeration {
      enum "cancel" {
        value 1;
        description
          "Cancel.";
      }
      enum "open" {
        value 0;
        description
          "Open.";
      }
    }
    description
      "Information of enum type driver-auto-upgrade-mode.";
  }

  typedef driver-default-states {
    type enumeration {
      enum "close" {
        value 0;
        description
          "Close.";
      }
      enum "open" {
        value 1;
        description
          "Open.";
      }
    }
    description
      "Information of enum type driver-default-states.";
  }  
  
  typedef driver-next-run-mode {
    type enumeration {
      enum "single" {
        value 1;
        description
          "Single.";
      }
      enum "virtual-cluster-chassis" {
        value 0;
        description
          "Virtual-cluster-chassis.";
      }
    }
    description
      "Information of enum type driver-next-run-mode.";
  }

  typedef board-channel-check-type {
    type enumeration {
      enum "enable" {
        value 1; 
        description
          "Enable.";
      }
      enum "disable" {
        value 2; 
        description
          "Disable.";
      }
    }
    description
      "Information of enum type board-channel-check-type.";
  }
  
  typedef driver-operation-flag {
    type enumeration {
      enum "enable" {
        value 1;
        description
          "Enable.";
      }
      enum "disable" {
        value 0;
        description
          "Disable.";
      }
    }
    description
      "Information of enum type driver-operation-flag.";
  }
  
  typedef driver-relation-type {
    type enumeration {
      enum "eq" {
        value 0;
        description
          "Equal.";
      }
      enum "ge" {
        value 1;
        description
          "Greate equal.";
      }
      enum "gt" {
        value 2;
        description
          "Greate.";
      }
      enum "le" {
        value 3;
        description
          "Little equal.";
      }
      enum "lt" {
        value 4;
        description
          "Little.";
      }
      enum "ne" {
        value 5;
        description
          "No equal.";
      }
    }
    description
      "Information of enum type driver-relation-type.";
  }
  
  typedef driver-alarm-level-type {
    type enumeration {
      enum "critical" {
        value 1;
        description
          "Critical.";
      }
      enum "major" {
        value 2;
        description
          "Major.";
      }
      enum "minor" {
        value 3;
        description
          "Minor.";
      }
      enum "warning" {
        value 4;
        description
          "Warning.";
      }
    }
    description
      "Information of enum type driver-alarm-level-type.";
  }

  typedef driver-board-device-type {
    type enumeration {
      enum "LPU" {
        value 0;
        description
          "LPU.";
      }
      enum "SFU" {
        value 1;
        description
          "SFU.";
      }
    }
    description
      "Information of enum type driver-board-device-type.";
  }
  
  typedef driver-clock-type {
    type enumeration {
      enum "syn-clock" {
        value 0;
        description
          "Synchronized clock.";
      }
      enum "line-clock" {
        value 1;
        description
          "Linear clock.";
      }
    }
    description
      "Information of enum type driver-clock-type.";
  }
  
  typedef driver-switch-mode-type {
    type enumeration {
      enum "auto-choice" {
        value 1;
        description
          "Automatic choice.";
      }
      enum "force-choice" {
        value 0;
        description
          "Forced choice.";
      }
    }
    description
      "Information of enum type driver-switch-mode-type.";
  }
  
  typedef driver-lock-state-type {
    type enumeration {
      enum "locked" {
        value 0;
        description
          "Locked.";
      }
      enum "unlocked" {
        value 1;
        description
          "Unlocked.";
      }
    }
    description
      "Information of enum type driver-lock-state-type.";
  }
 
  typedef driver-compatibility-state-type {
    type enumeration {
      enum "compatible" {
        value 0;
        description
          "State of compatible.";
      }
      enum "incompatible" {
        value 1;
        description
          "State of incompatible.";
      }
      enum "NA" {
        value 2;
        description
          "NA.";
      }
    }
    description
      "Information of enum type driver-compatibility-state-type.";
  }

  typedef driver-upgrade-suggestion-type {
    type enumeration {
      enum "recommend" {
        value 0;
        description
          "Recommend upgrade.";
      }
      enum "must" {
        value 1;
        description
          "Must upgrade.";
      }
      enum "NA" {
        value 2;
        description
          "NA.";
      }
    }
    description
      "Information of enum type driver-upgrade-suggestion-type.";
  }

  typedef driver-hardware-version-type {
    type enumeration {
      enum "EPLD" {
        value 0;
        description
          "Erasable programmable logic device.";
      }
      enum "canbus-chip2-sdr" {
        value 1;
        description
          "Sensor data record on a CANbus chip2.";
      }
      enum "canbus-sdr" {
        value 2;
        description
          "Sensor data record on a CANbus.";
      }
      enum "monitor-bus-software2" {
        value 3;
        description
          "Monitor BUS software2.";
      }
      enum "monitor-bus-software" {
        value 4;
        description
          "Monitor BUS software.";
      }
      enum "pic-epld" {
        value 5;
        description
          "Erasable programmable logic device on a PIC.";
      }
      enum "pic-sdr" {
        value 6;
        description
          "Sensor data record on a PIC.";
      }
      enum "NA" {
        value 7;
        description
          "NA.";
      }
      enum "cpu-epld" {
        value 8;
        description
          "Erasable programmable logic device on a CPU.";
      }
    }
    description
      "Information of enum type driver-hardware-version-type.";
  }

  typedef driver-check-result-type {
    type enumeration {
      enum "success" {
        value 0;
        description
          "Check version result is successful.";
      }
      enum "fail" {
        value 1;
        description
          "Check version result is failed.";
      }
    }
    description
      "Information of enum type driver-check-result-type.";
  }

  typedef lcs-improve-capacity-type {
    type enumeration {
      enum "480G" {
        value 480000;
        description
          "Upgrade to 480G.";
      }
      enum "800G" {
        value 800000;
        description
          "Upgrade to 800G.";
      }
      enum "1T2" {
        value 1200000;
        description
          "Upgrade to 1T2.";
      }
      enum "2T" {
        value 2000000;
        description
          "Upgrade to 2T.";
      }
      enum "600G" {
        value 600000;
        description
          "Upgrade to 600G.";
      }
    }
    description
      "Capacity. The capacity is related to a specific board.";
  }
  
  typedef lcs-active-status-type {
    type enumeration {
      enum "unallocated" {
        value 0;
        description
          "Unallocated.";
      }
      enum "activated" {
        value 1;
        description
          "Activated.";
      }
      enum "allocated" {
        value 2;
        description
          "Allocated.";
      }
    }
    description
      "License active status type.";
  }

  typedef driver-dcn-plane-mode-type {
    type enumeration {
      enum "dcn-control-plane" {
        value 0;
        description
          "DCN control plane.";
      }
      enum "dcn-management-plane" {
        value 1;
        description
          "DCN management plane.";
      }
    }
    description
      "DCN plane mode.";
  }

  typedef get-pm-input-mode-type {
    type enumeration {
      enum "default" {
        value 0;
        description
          "Default.";
      }
      enum "unknown" {
        value 1;
        description
          "Unknown.";
      }
      enum "standard" {
        value 85;
        description
          "Standard.";
      }
      enum "low-reliability" {
        value 170;
        description
          "Low-reliability.";
      }
    }
    description
      "Information of enum type pm-input-mode.";
  }

  typedef set-pm-input-mode-type {
    type enumeration {
      enum "default" {
        value 0;
        description
          "Default.";
      }
      enum "standard" {
        value 85;
        description
          "Standard.";
      }
      enum "low-reliability" {
        value 170;
        description
          "Low-reliability.";
      }
    }
    description
      "Information of enum type pm-input-mode.";
  }
  typedef disk-type {
    type enumeration {
      enum "hard-disk" {
        value 0;
        description
          "Hard disk.";
      }
      enum "usb-flash-drive" {
        value 1;
        description
          "USB flash drive.";
      }
    }
    description
      "Disk type.";
  }
  typedef led-color-type {
    type enumeration {
      enum "dim" {
        value 0;
        description
          "Dim.";
      }
      enum "red" {
        value 1;
        description
          "Red light.";
      }
      enum "green" {
        value 2;
        description
          "Green light.";
      }
      enum "yellow" {
        value 3;
        description
          "Yellow light.";
      }
    }
    description
      "Color of LED indicators.";
  }
  typedef led-class-type {
    type enumeration {
      enum "PWR" {
        value 0;
        description
          "Power module indicator.";
      }
      enum "MPU" {
        value 1;
        description
          "MPU indicator.";
      }
      enum "LPU" {
        value 2;
        description
          "LPU/SPU indicator.";
      }
      enum "SFU" {
        value 3;
        description
          "SFU indicator.";
      }
      enum "FAN" {
        value 4;
        description
          "Fan module indicator.";
      }
      enum "SYS" {
        value 5;
        description
          "System indicator.";
      }
      enum "USB" {
        value 6;
        description
          "USB indicator.";
      }
      enum "ICU" {
        value 7;
        description
          "ICU indicator.";
      }
      enum "CARD" {
        value 8;
        description
          "Card indicator.";
      }
    }
    description
      "Type of LED indicators.";
  }
  typedef driver-fiber-connect-mode {
    type enumeration {
      enum "half-fabric" {
        value 4;
        description
          "Half fabric.";
      }
      enum "full-fabric" {
        value 5;
        description
          "Full fabric.";
      }
    }
    description
      "Information of enum type fiber-connect-mode.";
  }
  typedef fiber-status {
    type enumeration {
      enum "los" {
        value 0;
        description
          "Fiber is abnormal.";
      }
      enum "mismatch" {
        value 1;
        description
          "Actual fiber length is not match configure fiber length.";
      }
      enum "off" {
        value 2;
        description
          "Fiber is off.";
      }
    }
    description
      "Information of enum type fiber-status.";
  }
  typedef service-forward-ability-type {
    type enumeration {
      enum "default" {
        value 0;
        description
          "Default.";
      }
      enum "480G" {
        value 1;
        description
          "480G.";
      }
      enum "1T" {
        value 2;
        description
          "1T.";
      }
    }
    description
      "Information of enum type service-forward-ability.";
  }
}
