/*
Copyright (C) 2019-2022 Huawei Technologies Co., Ltd. All rights reserved.
*/
module huawei-bras-diameter {
  namespace "urn:huawei:yang:huawei-bras-diameter";
  prefix bras-diameter;
  import huawei-extension {
    prefix ext;
  }
  ext:task-name "diameter";
  organization
    "Huawei Technologies Co., Ltd.";
  contact
    "Huawei Industrial Base
     Bantian, Longgang
     Shenzhen 518129
     People's Republic of China
     Website: http://www.huawei.com
     Email: support@huawei.com";
  description
    "Diameter.";
  revision 2022-09-05 {
    description
      "Modify description.";
    reference
      "Huawei private.";
  }
  revision 2019-03-23 {
    description
      "Init revision.";
    reference
      "Huawei private.";
  }

  container bras-diameter {
    description
      "Diameter.";
    container diameter {
      presence "Enables the Diameter protocol.";
      description
        "Configure the Diameter protocol.";
      container avp {
        description
        "Configure the AVP of the Diameter protocol.";
        container event-trigger {
          description
            "Configure the event-trigger avp.";
          leaf ignore-usage-report {
            type boolean;
            default "false";
            description
              "Enable/disable Event-Trigger(1006) AVP to ignore usage-report.";
          }
        }
        container monitor-key {
          description
            "Configure the monitor-key avp.";
          leaf parse-mode {
            type enumeration {
              enum "integer" {
                value 0;
                description
                  "Configure monitor key parse mode integer.";
              }
              enum "string" {
                value 1;
                description
                  "Configure monitor key parse mode string.";
              }
            }
            default "integer";
            description
              "Configure monitor key parse mode.";
          }
        }
      }
    }
  }
}
