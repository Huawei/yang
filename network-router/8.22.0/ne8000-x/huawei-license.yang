/*
Copyright (C) 2021-2022 Huawei Technologies Co., Ltd. All rights reserved.
*/
module huawei-license {
  namespace "urn:huawei:yang:huawei-license";
  prefix lcs;

  import huawei-pub-type {
    prefix pub-type;
  }
  import ietf-yang-types {
    prefix yang;
  }
  import huawei-extension {
    prefix ext;
  }
  import ietf-inet-types {
    prefix inet;
  }
  import huawei-ssl {
    prefix ssl;
  }

  organization
    "Huawei Technologies Co., Ltd.";
  contact
    "Huawei Industrial Base
     Bantian, Longgang
     Shenzhen 518129
     People's Republic of China
     Website: http://www.huawei.com
     Email: support@huawei.com";
  description
    "Proof of permission granted.";
  revision 2022-08-05 {
    description
      "The rtu-instances container, bandwidth-expect node, active-parameter-type node, and rtu-active-parameter-type type are added, and the policy-name node is configurable.";
    reference
      "Huawei private.";
  }
  revision 2022-06-24 {
    description
      "Modify the description of the upgrate-deadline node.";
    reference
      "Huawei private.";
  }
  revision 2022-06-21 {
    description
      "Add the /lcs:license/lcs:global container, and modify the contents of the resource-thresholds container.";
    reference
      "Huawei private.";
  }
  revision 2022-06-01 {
    description
      "Modify the description of the revoke-ticket node.";
    reference
      "Huawei private.";
  }
  revision 2022-05-19 {
    description
      "Add mandatory attribute.";
    reference
      "Huawei private.";
  }
  revision 2022-04-30 {
    description
      "Add license RTU service.";
    reference
      "Huawei private.";
  }
  revision 2022-04-20 {
    description
      "Modify the contents of the cloud-server2s container. Add rpc license-report-usage and license-refresh-item-state.";
    reference
      "Huawei private.";
  }
  revision 2022-03-12 {
    description
      "Change the node-ref of license-verify.";
    reference
      "Huawei private.";
  }
  revision 2022-02-24 {
    description
      "Add the license item status, the value is 'locked'.";
    reference
      "Huawei private.";
  }
  revision 2022-02-11 {
    description
      "Add rpc license-deactive, and modify the length of the strategy node.";
    reference
      "Huawei private.";
  }
  revision 2022-01-13 {
    description
      "Add the feature-resources container.";
    reference
      "Huawei private.";
  }
  revision 2021-12-08 {
    description
      "Modify the length of the server-name node.";
    reference
      "Huawei private.";
  }
  revision 2021-11-02 {
    description
      "Modify the contents of the resource-usages container.";
    reference
      "Huawei private.";
  }
  revision 2021-09-01 {
    description
      "Add statistics of cloud license support sparts.";
    reference
      "Huawei private.";
  }
  revision 2021-08-26 {
    description
      "Init revision.";
    reference
      "Huawei private.";
  }
  ext:task-name "license";
  typedef auth-type {
    type enumeration {
      enum "demo" {
        value 0;
        description
          "Demo of a license file.";
      }
      enum "commercial" {
        value 1;
        description
          "Commercial of a license file.";
      }
    }
    description
      "Type of license authority.";
  }
  typedef spec-type {
    type enumeration {
      enum "resource" {
        value 0;
        description
          "The resource of item.";
      }
      enum "function" {
        value 1;
        description
          "The function of item.";
      }
      enum "minimum" {
        value 2;
        description
          "The minimum of item.";
      }
      enum "default" {
        value 3;
        description
          "The default of item.";
      }
      enum "maximum" {
        value 4;
        description
          "The maximum of item.";
      }
    }
    description
      "Type of license spec.";
  }
  typedef state-type {
    type enumeration {
      enum "default" {
        value 0;
        description
          "To indicate the license activating state of the system, the value is 'default'.";
      }
      enum "trial" {
        value 1;
        description
          "To indicate the license activating state of the system, the value is 'trial'.";
      }
      enum "normal" {
        value 2;
        description
          "To indicate the license activating state of the system, the value is 'normal'.";
      }
      enum "emergency" {
        value 3;
        description
          "To indicate the license activating state of the system, the value is 'emergency'.";
      }
      enum "demo" {
        value 4;
        description
          "To indicate the license activating state of the system, the value is 'demo'.";
      }
    }
    description
      "Type of license state.";
  }
  typedef item-status-type {
    type enumeration {
      enum "default" {
        value 0;
        description
          "To indicate the license item status, the value is 'default'.";
      }
      enum "trial" {
        value 1;
        description
          "To indicate the license item status, the value is 'trial'.";
      }
      enum "normal" {
        value 2;
        description
          "To indicate the license item status, the value is 'normal'.";
      }
      enum "emergency" {
        value 3;
        description
          "To indicate the license item status, the value is 'emergency'.";
      }
      enum "demo" {
        value 4;
        description
          "To indicate the license item status, the value is 'demo'.";
      }
      enum "inactive" {
        value 5;
        description
          "To indicate the license item status, the value is 'inactive'.";
      }
      enum "locked" {
        value 6;
        description
          "To indicate the license item status, the value is 'locked'.";
      }
    }
    description
      "Type of license item status.";
  }
  typedef item-type {
    type enumeration {
      enum "resource" {
        value 0;
        description
          "The resource of license item.";
      }
      enum "function" {
        value 1;
        description
          "The function of license item.";
      }
    }
    description
      "Type of license item.";
  }
  typedef enable-status {
    type enumeration {
      enum "disable" {
        value 0;
        description
          "The disable status.";
      }
      enum "enable" {
        value 1;
        description
          "The enable status.";
      }
      enum "not-supported" {
        value 2;
        description
          "The not supported status.";
      }
    }
    description
      "Type of enable status.";
  }
  typedef mode-type {
    type enumeration {
      enum "common" {
        value 1;
        description
          "Common type.";
      }
      enum "cloud" {
        value 2;
        description
          "Cloud type.";
      }
    }
    description
      "Type of license mode.";
  }
  typedef register-state {
    type enumeration {
      enum "register" {
        value 1;
        description
          "Register state.";
      }
      enum "unregister" {
        value 2;
        description
          "Unregister state.";
      }
    }
    description
      "The register state.";
  }
  typedef connection-state {
    type enumeration {
      enum "online" {
        value 1;
        description
          "Online state.";
      }
      enum "offline" {
        value 2;
        description
          "Offline state.";
      }
      enum "offline-locked" {
        value 3;
        description
          "Offline locked state.";
      }
    }
    description
      "Status of the connection between the device and the cloud license server.";
  }
  typedef rtu-type {
    type enumeration {
      enum "board" {
        value 1;
        description
          "RTU type is board.";
      }
      enum "port" {
        value 2;
        description
          "RTU type is port.";
      }
      enum "application" {
        value 3;
        description
          "RTU type is application.";
      }
    }
    description
      "The RTU types.";
  }
  typedef rtu-parameter-type {
    type enumeration {
      enum "function" {
        value 1;
        description
          "RTU parameter type is function.";
      }
      enum "bandwidth" {
        value 2;
        description
          "RTU parameter type is bandwidth.";
      }
    }
    description
      "The RTU parameter types.";
  }
  typedef rtu-active-parameter-type {
    type enumeration {
      enum "na" {
        value 1;
        description
          "RTU activation parameter is not required.";
      }
      enum "bandwidth" {
        value 2;
        description
          "RTU activation parameter type is bandwidth.";
      }
    }
    description
      "The RTU activation parameter types.";
  }
  typedef rtu-start-type {
    type enumeration {
      enum "device" {
        value 1;
        description
          "RTU start type is device.";
      }
      enum "board" {
        value 2;
        description
          "RTU start type is board.";
      }
      enum "pic" {
        value 3;
        description
          "RTU start type is pic.";
      }
      enum "none" {
        value 4;
        description
          "RTU start type is none.";
      }
    }
    description
      "The start RTU types.";
  }
  container license {
    description
      "Proof of permission granted.";
    container global {
      description
        "Configure the global license configuration.";
      leaf threshold-alarm-disable {
        type boolean;
        default "false";
        description
          "Enable/disable the threshold alarm for all license items. If the value of this node is true, the configuration of the /lcs:license/lcs:resource-thresholds/lcs:resource-threshold/lcs:alarm-disable node will be ignored.";
      }
    }
    container global-states {
      config false;
      description
        "List of the global license informations.";
      list global-state {
        key "chassis-id";
        config false;
        description
          "Operational state of the global license information.";
        leaf chassis-id {
          type string {
            length "0..31";
          }
          config false;
          description
            "The device ID of a license file.";
        }
        leaf active-filename {
          type string {
            length "5..127";
          }
          config false;
          description
            "The name of a license file.";
        }
        leaf active-state {
          type state-type;
          config false;
          description
            "To indicate the license activating state of the system, the value can be 'normal' or 'default'.";
        }
        leaf startup-filename {
          type string {
            length "5..127";
          }
          config false;
          description
            "The name of the license file for the next startup.";
        }
        leaf revoke-ticket {
          type string {
            length "1..135";
          }
          config false;
          description
            "The revoke-ticket of a license file.";
        }
        leaf esn {
          type string {
            length "1..2047";
          }
          config false;
          description
            "The License ESN.";
        }
        leaf license-mode {
          type mode-type;
          config false;
          description
            "License mode.";
        }
      }
    }
    container license-items {
      description
        "List of all license items.";
      list license-item {
        ext:operation-exclude create;
        ext:generated-by system;
        key "name";
        description
          "Configure license item.";
        leaf name {
          type string {
            length "1..31";
          }
          description
            "License item name.";
        }
        leaf description {
          type string {
            length "1..255";
          }
          config false;
          description
            "The description of a license item.";
        }
        leaf default-value {
          type uint32;
          config false;
          description
            "The default value of a license item.";
        }
        leaf maximum-value {
          type uint32;
          config false;
          description
            "The maximum value of a license item.";
        }
        leaf current-value {
          type uint32;
          config false;
          description
            "The current value of a license item.";
        }
        leaf used-value {
          type uint32;
          config false;
          description
            "The usage value of a license item.";
        }
        leaf status {
          type item-status-type;
          config false;
          description
            "The status of a license item.";
        }
        leaf expired-date {
          type string {
            length "1..71";
          }
          config false;
          description
            "The expired date of a license item.";
        }
        leaf type {
          type item-type;
          config false;
          description
            "The type of a license item.";
        }
        leaf trial-state {
          type enable-status;
          config false;
          description
            "Trial status of a control item.";
        }
        leaf trial-remain-day {
          type uint32;
          config false;
          description
            "Remaining trial days of a license control item.";
        }
        leaf trial-remain-times {
          type uint32;
          config false;
          description
            "Remaining trial times of a license control item.";
        }
      }
    }
    container license-sale-items {
      config false;
      description
        "List of all license saleitems.";
      list license-sale-item {
        key "name";
        config false;
        description
          "Operational state of license saleitem.";
        leaf name {
          type string {
            length "1..31";
          }
          config false;
          description
            "License saleitem name.";
        }
        leaf description {
          type string {
            length "1..255";
          }
          config false;
          description
            "The description of a license saleitem.";
        }
        leaf sale-value {
          type uint32;
          config false;
          description
            "The sales value of a license saleitem.";
        }
        container sub-sale-items {
          config false;
          description
            "List of all license sub saleitems.";
          list sub-sale-item {
            key "name";
            description
              "Operational state of license sub saleitem.";
            leaf name {
              type string {
                length "1..31";
              }
              description
                "License sub saleitem name.";
            }
            leaf description {
              type string {
                length "1..255";
              }
              description
                "The description of a license sub saleitem.";
            }
            leaf sale-value {
              type uint32;
              description
                "The sales value of a license sub saleitem.";
            }
            container license-items {
              description
                "List of all license items.";
              list license-item {
                key "name";
                description
                  "Operational state of license item.";
                leaf name {
                  type string {
                    length "1..31";
                  }
                  description
                    "License item name.";
                }
                leaf description {
                  type string {
                    length "1..255";
                  }
                  description
                    "The description of a license item.";
                }
                leaf default-value {
                  type uint32;
                  description
                    "The default value of a license item.";
                }
                leaf maximum-value {
                  type uint32;
                  description
                    "The maximum value of a license item.";
                }
                leaf current-value {
                  type uint32;
                  description
                    "The current value of a license item.";
                }
                leaf used-value {
                  type uint32;
                  description
                    "The usage value of a license item.";
                }
                leaf status {
                  type item-status-type;
                  description
                    "The status of a license item.";
                }
                leaf expired-date {
                  type string {
                    length "1..71";
                  }
                  description
                    "The expired date of a license item.";
                }
                leaf type {
                  type item-type;
                  description
                    "The type of a license item.";
                }
                leaf trial-state {
                  type enable-status;
                  description
                    "Trial status of a control item.";
                }
                leaf trial-remain-day {
                  type uint32;
                  description
                    "Remaining trial days of a license control item.";
                }
                leaf trial-remain-times {
                  type uint32;
                  description
                    "Remaining trial times of a license control item.";
                }
              }
            }
          }
        }
        container license-items {
          description
            "List of all license items.";
          list license-item {
            key "name";
            description
              "Operational state of license item.";
            leaf name {
              type string {
                length "1..31";
              }
              description
                "License item name.";
            }
            leaf description {
              type string {
                length "1..255";
              }
              config false;
              description
                "The description of a license item.";
            }
            leaf default-value {
              type uint32;
              config false;
              description
                "The default value of a license item.";
            }
            leaf maximum-value {
              type uint32;
              config false;
              description
                "The maximum value of a license item.";
            }
            leaf current-value {
              type uint32;
              config false;
              description
                "The current value of a license item.";
            }
            leaf used-value {
              type uint32;
              config false;
              description
                "The usage value of a license item.";
            }
            leaf status {
              type item-status-type;
              config false;
              description
                "The status of a license item.";
            }
            leaf expired-date {
              type string {
                length "1..71";
              }
              config false;
              description
                "The expired date of a license item.";
            }
            leaf type {
              type item-type;
              config false;
              description
                "The type of a license item.";
            }
            leaf trial-state {
              type enable-status;
              config false;
              description
                "Trial status of a control item.";
            }
            leaf trial-remain-day {
              type uint32;
              config false;
              description
                "Remaining trial days of a license control item.";
            }
            leaf trial-remain-times {
              type uint32;
              config false;
              description
                "Remaining trial times of a license control item.";
            }
          }
        }
      }
    }
    container stack-sale-items {
      config false;
      description
        "List of all license sale items.";
      list stack-sale-item {
        key "chassis-id";
        config false;
        description
          "Operational state of license sale item.";
        leaf chassis-id {
          type string {
            length "0..31";
          }
          config false;
          description
            "The device ID of license sale item.";
        }
        container license-sale-items {
          config false;
          description
            "List of all license saleitems.";
          list license-sale-item {
            key "name";
            config false;
            description
              "Operational state of license saleitem.";
            leaf name {
              type string {
                length "1..31";
              }
              config false;
              description
                "License saleitem name.";
            }
            leaf description {
              type string {
                length "1..255";
              }
              config false;
              description
                "The description of a license saleitem.";
            }
            leaf sale-value {
              type uint32;
              config false;
              description
                "The sales value of a license saleitem.";
            }
            container license-items {
              description
                "List of all license items.";
              list license-item {
                key "name";
                description
                  "Operational state of license item.";
                leaf name {
                  type string {
                    length "1..31";
                  }
                  description
                    "License item name.";
                }
                leaf description {
                  type string {
                    length "1..255";
                  }
                  config false;
                  description
                    "The description of a license item.";
                }
                leaf default-value {
                  type uint32;
                  config false;
                  description
                    "The default value of a license item.";
                }
                leaf maximum-value {
                  type uint32;
                  config false;
                  description
                    "The maximum value of a license item.";
                }
                leaf current-value {
                  type uint32;
                  config false;
                  description
                    "The current value of a license item.";
                }
                leaf used-value {
                  type uint32;
                  config false;
                  description
                    "The usage value of a license item.";
                }
                leaf status {
                  type item-status-type;
                  config false;
                  description
                    "The status of a license item.";
                }
                leaf expired-date {
                  type string {
                    length "1..71";
                  }
                  config false;
                  description
                    "The expired date of a license item.";
                }
                leaf type {
                  type item-type;
                  config false;
                  description
                    "The type of a license item.";
                }
                leaf trial-state {
                  type enable-status;
                  config false;
                  description
                    "Trial status of a control item.";
                }
                leaf trial-remain-day {
                  type uint32;
                  config false;
                  description
                    "Remaining trial days of a license control item.";
                }
                leaf trial-remain-times {
                  type uint32;
                  config false;
                  description
                    "Remaining trial times of a license control item.";
                }
              }
            }
          }
        }
      }
    }
    container spec-items {
      config false;
      description
        "List of all specific license items.";
      list spec-item {
        key "name";
        config false;
        description
          "Operational state of specific license item.";
        leaf name {
          type string {
            length "0..63";
          }
          config false;
          description
            "The name of a specific item.";
        }
        leaf description {
          type string {
            length "0..127";
          }
          config false;
          description
            "Description of the specification.";
        }
        leaf current-value {
          type uint32;
          config false;
          description
            "The value of a specific item.";
        }
        leaf type {
          type spec-type;
          config false;
          description
            "The type of a specific item.";
        }
        leaf default-value {
          type uint32;
          config false;
          description
            "The specification default value.";
        }
        leaf minimum-value {
          type uint32;
          config false;
          description
            "The specification minimum value.";
        }
        leaf maximum-value {
          type uint32;
          config false;
          description
            "The specification maximum value.";
        }
      }
    }
    container license-files {
      config false;
      description
        "List of all information of a license file.";
      list license-file {
        key "chassis-id filename";
        config false;
        description
          "Operational state of the information of a license file.";
        leaf chassis-id {
          type string {
            length "0..31";
          }
          config false;
          description
            "The device ID of a license file.";
        }
        leaf filename {
          type string {
            length "5..127";
          }
          config false;
          description
            "The name of a license file.";
        }
        leaf filesize {
          type uint32;
          config false;
          description
            "The size of a license file.";
        }
        container general {
          config false;
          description
            "Operational state of the general information of a license file.";
          leaf serial-number {
            type string {
              length "0..63";
            }
            config false;
            description
              "The serial number of a license file.";
          }
          leaf creator {
            type string {
              length "0..63";
            }
            config false;
            description
              "The creator of a license file.";
          }
          leaf created-time {
            type yang:date-and-time;
            config false;
            description
              "The created time of a license file.";
          }
          leaf country {
            type string {
              length "0..63";
            }
            config false;
            description
              "The country information of a license file.";
          }
          leaf customer {
            type string {
              length "0..63";
            }
            config false;
            description
              "The customer information of a license file.";
          }
          leaf office {
            type string {
              length "0..63";
            }
            config false;
            description
              "The office information of a license file.";
          }
          leaf file-expired-date {
            type pub-type:date;
            description
              "The expired date of a license file.";
          }
        }
        container features {
          config false;
          description
            "List of all the feature information of a license file.";
          list feature {
            key "name";
            config false;
            description
              "Operational state of the feature information of a license file.";
            leaf name {
              type string {
                length "0..63";
              }
              config false;
              description
                "The feature information name of a license file.";
            }
            leaf product {
              type string {
                length "0..63";
              }
              config false;
              description
                "The product information of a license file.";
            }
            leaf esn {
              type string {
                length "0..2055";
              }
              config false;
              description
                "The ESN of a license file.";
            }
            leaf auth-type {
              type auth-type;
              config false;
              description
                "The authorizing type of a license file.";
            }
            leaf running-deadline {
              type pub-type:date;
              config false;
              description
                "The running deadline of a license file.";
            }
            leaf trial-days {
              type uint32;
              config false;
              description
                "List of the trial days of a license file.";
            }
            leaf software-deadline {
              type pub-type:date;
              config false;
              description
                "The software deadline of a license file.";
            }
            leaf hardware-deadline {
              type pub-type:date;
              config false;
              description
                "The hardware deadline of a license file.";
            }
            leaf upgrate-deadline {
              type pub-type:date;
              config false;
              description
                "The upgrade deadline of a license file.";
            }
            container feature-items {
              config false;
              description
                "List of all feature items of a license file.";
              list feature-item {
                key "name";
                config false;
                description
                  "Operational state of feature item of a license file.";
                leaf name {
                  type string {
                    length "0..63";
                  }
                  config false;
                  description
                    "Feature item name of a license file.";
                }
                leaf value {
                  type uint32;
                  config false;
                  description
                    "Feature item value of a license file.";
                }
              }
            }
          }
        }
      }
    }
    container resource-usages {
      config false;
      description
        "List of all license resource usages.";
      list resource-usage {
        key "name";
        description
          "Operational state of license resource usage.";
        leaf name {
          type string {
            length "0..31";
          }
          description
            "The name of resource item.";
        }
        leaf usage {
          type uint32;
          description
            "The usage of resource item.";
        }
        leaf active-value {
          type uint32;
          description
            "The active value of resource item.";
        }
        container license-items {
          description
            "List of all license items.";
          list license-item {
            key "name";
            description
              "Operational state of license item.";
            leaf name {
              type string {
                length "1..31";
              }
              description
                "License item name.";
            }
            leaf current-value {
              type uint32;
              description
                "The current value of a license item.";
            }
            leaf used-value {
              type uint32;
              description
                "The usage value of a license item.";
            }
          }
        }
      }
    }
    container resource-thresholds {
      description
        "List of license resource usage thresholds.";
      list resource-threshold {
        key "name";
        description
          "Configure license resource usage threshold.";
        leaf name {
          type string {
            length "0..31";
          }
          description
            "Name of a license resource control item.";
        }
        leaf threshold {
          type uint32 {
            range "50..95";
          }
          description
            "Usage threshold of a license control resource item.";
        }
        leaf configurable-switch {
          type uint32 {
            range "0..1";
          }
          default "0";
          config false;
          description
            "Configurable flag of a license resource item.";
        }
        leaf description {
          type string {
            length "0..255";
          }
          config false;
          description
            "Description of a license resource control item.";
        }
        leaf alarm-disable {
          type boolean;
          default "false";
          description
            "Enable/disable the threshold alarm.";
        }
      }
    }
    container feature-resources {
      config false;
      description
        "List of all license resource items required by the feature.";
      list feature-resource {
        key "feature-name";
        description
          "Operational state of license resource items required by the feature.";
        leaf feature-name {
          type string {
            length "1..63";
          }
          description
            "Feature name.";
        }
        leaf strategy {
          type string {
            length "1..255";
          }
          description
            "License strategy.";
        }
        container global-items {
          description
            "List of all global license resource items.";
          list global-item {
            key "item-name";
            description
              "Operational state of global license resource items.";
            leaf item-name {
              type string {
                length "1..31";
              }
              description
                "License item name.";
            }
            leaf description {
              type string {
                length "1..255";
              }
              description
                "The description of the license item.";
            }
            leaf unit {
              type string {
                length "1..63";
              }
              description
                "The unit of the license item.";
            }
            leaf item-num {
              type string {
                length "1..15";
              }
              description
                "The number of the license item.";
            }
            leaf strategy {
              type string {
                length "1..3";
              }
              description
                "The strategy of the license item.";
            }
          }
        }
        container board-items {
          description
            "List of all board license resource items.";
          list board-item {
            key "board item-name";
            description
              "Operational state of board license resource items.";
            leaf board {
              type string {
                length "1..31";
              }
              description
                "Board position.";
            }
            leaf item-name {
              type string {
                length "1..31";
              }
              description
                "License item name.";
            }
            leaf description {
              type string {
                length "1..255";
              }
              description
                "The description of the license item.";
            }
            leaf unit {
              type string {
                length "1..63";
              }
              description
                "The unit of the license item.";
            }
            leaf item-num {
              type string {
                length "1..15";
              }
              description
                "The number of the license item.";
            }
            leaf strategy {
              type string {
                length "1..3";
              }
              description
                "The strategy of the license item.";
            }
          }
        }
        container port-items {
          description
            "List of all port license resource items.";
          list port-item {
            key "port item-name";
            description
              "Operational state of port license resource items.";
            leaf port {
              type string {
                length "1..63";
              }
              description
                "Port position.";
            }
            leaf item-name {
              type string {
                length "1..31";
              }
              description
                "License item name.";
            }
            leaf description {
              type string {
                length "1..255";
              }
              description
                "The description of the license item.";
            }
            leaf unit {
              type string {
                length "1..63";
              }
              description
                "The unit of the license item.";
            }
            leaf item-num {
              type string {
                length "1..15";
              }
              description
                "The number of the license item.";
            }
            leaf strategy {
              type string {
                length "1..3";
              }
              description
                "The strategy of the license item.";
            }
          }
        }
      }
    }
    container cloud-servers {
      status deprecated;
      description
        "List of cloud license servers. The node /lcs:license/lcs:cloud-servers/lcs:cloud-server is deprecated. You are advised to use the node /lcs:license/lcs:cloud-server2s/lcs:cloud-server2.";
      list cloud-server {
        key "server-ip server-port";
        max-elements  "1";
        status deprecated;
        description
          "Configure cloud license server.";
        leaf server-ip {
          type inet:ipv4-address-no-zone;
          status deprecated;
          description
            "The IP address of cloud license server.";
        }
        leaf server-port {
          type uint32 {
            range "1..65535";
          }
          status deprecated;
          description
            "The port of cloud license server.";
        }
        leaf register-state {
          type register-state;
          config false;
          status deprecated;
          description
            "The register state with cloud license server.";
        }
        leaf policy-name {
          type string {
            length "1..255";
          }
          config false;
          status deprecated;
          description
            "The policy name.";
        }
      }
    }
    container cloud-server2s {
      description
        "List of cloud license servers.";
      list cloud-server2 {
        key "server-name";
        max-elements "1";
        description
          "Configure cloud license server.";
        leaf server-name {
          type string {
            length "5..127";
          }
          description
            "Name of the cloud license server.";
        }
        leaf server-ip {
          type inet:ipv4-address-no-zone;
          mandatory true;
          description
            "The IP address of cloud license server.";
        }
        leaf server-port {
          type uint32 {
            range "1..65535";
          }
          mandatory true;
          description
            "The port of cloud license server.";
        }
        leaf register-state {
          type register-state;
          config false;
          description
            "The register state with cloud license server.";
        }
        leaf policy-name {
          type leafref {
            path "/ssl:ssl/ssl:ssl-policys/ssl:ssl-policy/ssl:policy-name";
          }
          mandatory true;
          description
            "The policy name.";
        }
        leaf connection-state {
          type connection-state;
          config false;
          description
            "Status of the connection between the device and the cloud license server.";
        }
        leaf remaining-days {
          when "../connection-state='offline'";
          type uint32 {
            range 1..60;
          }
          config false;
          description
            "Remaining days of device offline locking.";
        }
      }
    }
    container support-sparts {
      config false;
      description
        "List of cloud license support sparts.";
      list support-spart {
        key "spart-name";
        description
          "Statistics of cloud license support sparts.";
        leaf spart-name {
          type string {
            length "1..32";
          }
          description
            "License spart name.";
        }
      }
    }
    container rtu-models {
      config false;
      description
        "List of RTU model, which describes the parameter types.";
      list rtu-model {
        key "rtu-type application-name";
        config false;
        description
          "Statistics of RTU model, which describes the parameter types.";
        leaf rtu-type {
          type rtu-type;
          description
            "The RTU type.";
        }
        leaf application-name {
          type string {
            length "1..31";
          }
          description
            "The application name.";
        }
        leaf rtu-parameter-type {
          type rtu-parameter-type;
          description
            "The RTU parameter types.";
        }
      }
    }
    container rtu-bandwidth-params {
      config false;
      description
        "List of parameter of bandwidth type RTU.";
      list rtu-bandwidth-param {
        key "rtu-type position application-name";
        config false;
        description
          "Statistics of the parameter of bandwidth type RTU.";
        leaf rtu-type {
          type rtu-type;
          description
            "The RTU type.";
        }
        leaf position {
          type pub-type:position;
          description
            "Board position in standard notation, serial-port position is like[1/1/1/1:2:3].";
        }
        leaf application-name {
          type string {
            length "1..31";
          }
          description
            "The application name.";
        }
        leaf bandwidth-min {
          type uint32;
          description
            "Minimum Bandwidth.";
        }
        leaf bandwidth-max {
          type uint32;
          description
            "Maximum Bandwidth.";
        }
        leaf bandwidth-current {
          type uint32;
          description
            "Current Bandwidth.";
        }
        leaf bandwidth-expect {
          type uint32;
          description
            "Expected bandwidth.";
        }
        leaf rtu-start-type {
          type rtu-start-type;
          description
            "The start RTU types.";
        }
        leaf rtu-start-position {
          type pub-type:position;
          description
            "Physical position to which the start RTU belongs.";
        }
        leaf active-parameter-type {
          type rtu-active-parameter-type;
          description
            "The RTU activation parameter type.";
        }
        container sale-items {
          description
            "List of all license sales items.";
          list sale-item {
            key "name";
            config false;
            description
              "Statistics of license sales item.";
            leaf name {
              type string {
                length "1..31";
              }
              description
                "The sales item name.";
            }
            leaf slice-factor {
              type uint32;
              description
                "Split a single sales item to a specified number of pieces.";
            }
            leaf slice-number {
              type uint32;
              description
                "The number of slices of a sales item.";
            }
          }
        }
      }
    }
    container rtu-start-infos {
      config false;
      description
        "List of start RTU information.";
      list rtu-start-info {
        key "rtu-type position application-name start-sale-name";
        config false;
        description
          "Statistics of start RTU information.";
        leaf rtu-type {
          type rtu-type;
          description
            "The RTU type.";
        }
        leaf position {
          type pub-type:position;
          description
            "Board position in standard notation, serial-port position is like[1/1/1/1:2:3].";
        }
        leaf application-name {
          type string {
            length "1..31";
          }
          description
            "The application name.";
        }
        leaf start-sale-name {
          type string {
            length "1..31";
          }
          description
            "The license start sales item.";
        }
        container sale-items {
          config false;
          description
            "List of expansion sales items corresponding to the start RTU.";
          list sale-item {
            key "name";
            config false;
            description
              "Statistics of license sales item.";
            leaf name {
              type string {
                length "1..31";
              }
              description
                "The sales item name.";
            }
            leaf slice-factor {
              type uint32;
              description
                "Split a single sales item to a specified number of pieces.";
            }
            leaf slice-number {
              type uint32;
              description
                "The number of slices of a sales item.";
            }
          }
        }
      }
    }
    container rtu-instances {
      description
        "List of RTU instances.";
      list rtu-instance {
        key "rtu-type position application-name";
        description
          "Configure RTU instance.";
        leaf rtu-type {
          type rtu-type;
          description
            "The RTU type.";
        }
        leaf position {
          type pub-type:position;
          description
            "Board position in standard notation, serial-port position is like[1/1/1/1:2:3].";
        }
        leaf application-name {
          type string {
            length "1..31";
          }
          description
            "The application name.";
        }
        choice parameter {
          description
            "RTU parameters.";
          case bandwidth {
            description
              "The parameter type is bandwidth.";
            leaf bandwidth {
              type uint32;
              description
                "Bandwidth of the RTU.";
            }
          }
        }
      }
    }
  }
  rpc license-active {
    description
      "To active a license file.";
    input {
      leaf filename {
        type string {
          length "5..127";
        }
        description
          "The name of a license file.";
      }
    }
  }
  rpc license-startup {
    description
      "To set the license file for the next startup.";
    input {
      leaf filename {
        type string {
          length "5..127";
        }
        mandatory true;
        description
          "The name of the license file for the next startup.";
      }
    }
  }
  rpc license-deactive {
    description
      "To deactive a license file.";
  }
  rpc license-revoke {
    description
      "To revoke a license file.";
  }
  rpc license-verify {
    description
      "To verify a license file.";
    ext:node-ref "/license/license-files/license-file/filename";
    input {
      leaf filename {
        type string {
          length "5..127";
        }
        description
          "The name of a license file.";
      }
    }
  }
  rpc license-revoke-chassis {
    description
      "To revoke a license file by device ID.";
    input {
      leaf chassis-id {
        type string {
          length "1..31";
        }
        description
          "The device ID of revoke license action.";
      }
    }
  }
  rpc license-delete {
    description
      "To delete a license file in $_license.";
    input {
      leaf filename {
        type string {
          length "1..127";
        }
        description
          "The name of a license file.";
      }
    }
  }
  rpc license-trial {
    description
      "Enable or disable the trial of a specific control item.";
    input {
      leaf trial-switch {
        type boolean;
        mandatory true;
        description
          "Whether to enable or disable the trial function of a control item.";
      }
    }
  }
  rpc license-export {
    description
      "Export the license to a file.";
    input {
      leaf filename {
        type string {
          length "5..127";
        }
        description
          "The file name of exporting license.";
      }
    }
  }
  rpc startup-paf {
    description
      "Configure an existing PAF file as the startup PAF file.";
    input {
      leaf filename {
        type string {
          length "5..48";
        }
        mandatory true;
        description
          "Name of a PAF file.";
      }
    }
  }
  rpc license-emergency {
    description
      "To activate license emergency mode.";
  }
  rpc license-assign {
    description
      "Assign cloud license.";
    input {
      leaf item-name {
        type string {
          length "1..31";
        }
        description
          "License item.";
      }
      leaf item-num {
        type uint32;
        description
          "License number.";
      }
    }
  }
  rpc license-smooth {
    description
      "Smooth license.";
  }
  rpc license-report-usage {
    description
      "Report the license resource usage.";
  }
  rpc license-refresh-item-state {
    description
      "Refresh the license item state from the cloud server.";
    input  {
      leaf item-name {
        type string {
          length "1..31";
        }
        description
          "Name of the license item. If the item name is not specified, all items are refreshed.";
      }
    }
  }
  rpc license-switch-mode {
    description
      "Switch license mode.";
    input {
      leaf license-mode {
        type mode-type;
        mandatory true;
        description
          "License mode.";
      }
    }
  }
  rpc license-calculate-rtu-resource {
    description
      "Calculate the type and number of RTU sales items.";
    input  {
      container calculate-rtu-resources {
        description
          "List of calculate the type and number of RTU sales items.";
        list calculate-rtu-resource {
          key "rtu-type position application-name";
          description
            "Calculate the type and number of RTU sales items.";
          leaf rtu-type {
            type rtu-type;
            description
              "The RTU type.";
          }
          leaf position {
            type pub-type:position;
            description
              "Board position in standard notation, serial-port position is like[1/1/1/1:2:3].";
          }
          leaf application-name {
            type string {
              length "1..31";
            }
            description
              "The application name.";
          }
          leaf bandwidth {
            type uint32;
            mandatory true;
            description
              "Used to calculate the bandwidth of a sales item.";
          }
        }
      }
    }
    output  {
      container calculated-results {
        description
          "List of calculation result.";
        list calculated-result {
          key "rtu-type position application-name";
          description
            "Calculation result.";
          leaf rtu-type {
            type rtu-type;
            description
              "The RTU type.";
          }
          leaf position {
            type pub-type:position;
            description
              "Board position in standard notation, serial-port position is like[1/1/1/1:2:3].";
          }
          leaf application-name {
            type string {
              length "1..31";
            }
            description
              "The application name.";
          }
          leaf bandwidth {
            type uint32;
            description
              "Indicates the bandwidth supported by the device that is the upward value to the bandwidth used for calculation.";
          }
          container sale-items {
            description
              "List of all license sales items.";
            list sale-item {
              key "name";
              description
                "The license sales item.";
              leaf name {
                type string {
                  length "1..31";
                }
                description
                  "The sales item name.";
              }
              leaf slice-factor {
                type uint32;
                description
                  "Split a single sales item to a specified number of pieces.";
              }
              leaf slice-number {
                type uint32;
                description
                  "The number of slices of a sales item.";
              }
            }
          }
        }
      }
    }
  }
}
