/*
Copyright (C) 2020-2022 Huawei Technologies Co., Ltd. All rights reserved.
*/
module huawei-ifit-common {
  yang-version 1;
  namespace "urn:huawei:yang:huawei-ifit-common";
  prefix ifit-common;
  import huawei-ifit {
    prefix ifit;
  }
  import huawei-extension {
    prefix ext;
  } 
  import ietf-inet-types {
    prefix inet;
  }
  import huawei-ifm {
    prefix ifm;
  }
  import huawei-network-instance {
    prefix ni;
  }
  import huawei-l3vpn {
    prefix l3vpn;
  }

  import huawei-evpl {
    prefix evpl;
  }
  import huawei-apn {
    prefix apn;
  }

  import huawei-evpn {
    prefix evpn;
  }
  import huawei-bd {
    prefix bd;
  }
  import huawei-pub-type {
    prefix pub-type;
  }  
  organization
    "Huawei Technologies Co., Ltd.";
  contact
    "Huawei Industrial Base
     Bantian, Longgang
     Shenzhen 518129
     People's Republic of China
     Website: http://www.huawei.com
     Email: support@huawei.com";
  description
    "This module contains a collection of YANG definitions IFIT feature.";
  revision 2022-08-27 {
    description
      "Modify description.";
    reference
      "Huawei private.";
  }
  revision 2022-07-12 {
    description
      "Add keys for the dynamic-flow-hops container.";
    reference
      "Huawei private.";
  }
  revision 2022-07-05 {
    description
      "Modify period time second.";
    reference
      "Huawei private.";
  }
  revision 2022-06-25 {
    description
      "Delete flow-apn and add APN flow.";
    reference
      "Huawei private.";
  }
  revision 2022-06-23 {
    description
      "Modify flow direction.";
    reference
      "Huawei private.";
  }
  revision 2022-06-08 {
    description
      "Add EVPN flow.";
    reference
      "Huawei private.";
  }
  revision 2022-05-28 {
    description
      "Add single device measure.";
    reference
      "Huawei private.";
  }
  revision 2022-04-22 {
    description
      "Add flow-apn.";
    reference
      "Huawei private.";
  }
  revision 2022-03-23 {
    description
      "Add mapping color flag.";
    reference
      "Huawei private.";
  }
  revision 2022-03-22 {
    description
      "Add period time second.";
    reference
      "Huawei private.";
  }
  revision 2022-03-09 {
    description
      "Add instance-ht16.";
    reference
      "Huawei private.";
  }
  revision 2022-03-02 {
    description
      "Modify flow direction.";
    reference
      "Huawei private.";
  }
  revision 2022-01-17 {
    description
      "Modify bind-learning-interfaces.";
    reference
      "Huawei private.";
  }
  revision 2021-12-22 {
    description
      "Modify data type of flow-statistic-results.";
    reference
      "Huawei private.";
  }
  revision 2020-04-08 {
    description
      "Initial revision.";
    reference
      "Huawei private.";
  }
  ext:task-name  "ifit";
  typedef flow-type {
    type enumeration {
      enum "unidirection" {
        value 2;
        description
          "An unidirection IFIT flow.";
      }
      enum "bidirection" {
        value 1;
        description
          "A bidirection IFIT flow.";
      }
    }
	description
      "Flow type.";
  }
  typedef measure-mode {
    type enumeration {
      enum "e2e" {
        value 1;
        description
          "E2E measure mode.";
      }
      enum "trace" {
        value 2;
        description
          "Trace measure mode.";
      }
    }
	description
      "Measure mode.";
  }
   typedef addr-type {
    type enumeration {
      enum "ipv4" {
        value 0;
        description
          "IPv4 address.";
      }
      enum "ipv6" {
        value 1;
        description
          "IPv6 address.";
      }
    }
	description
      "Address type.";
  }
  typedef flow-direction {
    type enumeration {
      enum "ingress" {
        value 1;
        description
          "Ingress of an IFIT flow.";
      }
      enum "transit-input" {
        value 2;
        description
          "Transit input of an IFIT flow.";
      }
      enum "transit-output" {
        value 3;
        description
          "Transit output of an IFIT flow.";
      }
      enum "egress" {
        value 4;
        description
          "Egress of an IFIT flow.";
      }
      enum "ingress-output" {
        value 5;
        description
          "Ingress output of an IFIT flow.";
      }
      enum "egress-input" {
        value 6;
        description
          "Egress input of an IFIT flow.";
      }
      enum "egress-to-cpu" {
        value 7;
        description
          "Egress to cpu of an IFIT flow.";
      }
      enum "egress-normal-drop" {
        value 8;
        description
          "Normal drop of an IFIT flow.";
      }
      enum "conversion-input" {
        value 9;
        description
          "Conversion input of an IFIT flow.";
      }
      enum "conversion-output" {
        value 10;
        description
          "Conversion output of an IFIT flow.";
      }
      enum "egress-bum" {
        value 11;
        description 
          "Egress BUM of an IFIT flow.";
      }
    }
	description
      "Flow direction.";
  }
  typedef addr-family-type {
    type enumeration {
      enum "ipv4-unicast" {
        value 1;
        description
          "IPv4 unicast.";
      }
      enum "ipv6-unicast" {
        value 2;
        description
          "IPv6 unicast.";
      }
    }
    description
      "Address family.";
  }
  typedef learning-mode {
    type enumeration {
      enum "sip-mask-dip-exact" {
        value 1;
        description
          "Mask included for source IP matching, and exact matching for destination IP address.";
      }
      enum "sip-mask-dip-mask" {
        value 2;
        description
          "Mask included for source and destination IP matching.";
      }
      enum "sip-exact-dip-exact" {
        value 3;
        description
          "Exact matching for source and destination IP addresses.";
      }
      enum "sip-exact-dip-mask" {
        value 4;
        description
          "Exact matching for source IP address, and mask included for destination IP matching.";
      }
    }
    description
      "Learning mode.";
  }

  typedef mapping-type {
    type enumeration {
      enum "ingress" {
        value 1;
        description
          "Ingress.";
      }
      enum "egress" {
        value 2;
        description
          "Egress.";
      }
    }
     description
      "Mapping type.";
  }
  typedef clock-mode-type {
    type enumeration {
      enum "common" {
        value 0;
        description
          "Common-precision clock mode.";
      }
      enum "precision-sampling" {
        value 1;
        description
          "High-precision sampling clock mode.";
      }
      enum "precision-full" {
        value 2;
        description
          "High-precision full clock mode.";
      }
    }
    description
      "Clock mode.";
  }
  typedef whitelist-group-mode {
    type enumeration {
      enum "common" {
        value 0;
        description
          "Common mode.";
      }
      enum "native-ip" {
        value 1;
        description
          "Native IP mode.";
      }
    }
    description
      "Whitelist group mode.";
  }
  typedef native-ip-color-flag {
    type enumeration {
      enum "flags-bit0" {
        value 0;
        description
          "Coloring at bit 0 of flags.";
      }
      enum "tos-bit3" {
        value 3;
        description
          "Coloring at bit 3 of ToS.";
      }
      enum "tos-bit4" {
        value 4;
        description
          "Coloring at bit 4 of ToS.";
      }
      enum "tos-bit5" {
        value 5;
        description
          "Coloring at bit 5 of ToS.";
      }
      enum "tos-bit6" {
        value 6;
        description
          "Coloring at bit 6 of ToS.";
      }
      enum "tos-bit7" {
        value 7;
        description
          "Coloring at bit 7 of ToS.";
      }
    }
    description
      "Color flag of IFIT for native IP.";
  }
  typedef work-mode {
    type enumeration {
      enum "mcp" {
        value 1;
        description
          "MCP.";
      }
      enum "dcp" {
        value 2;
        description
          "DCP.";
      }
      enum "auto" {
        value 3;
        description
          "AUTO.";
      }
    }
    description
      "Work mode of IFIT.";
  }
  typedef service-type {
    type enumeration {
      enum "srv6-segment-list" {
        value 1;
        description
          "SRv6 segment list.";
      }
    }
    description
      "Service type of IFIT.";
  }
  typedef interval-type {
    type enumeration {
      enum "1s" {
        value 0;
        description
          "Measurement interval is 1 second.";
      }
      enum "10s" {
        value 1;
        description
          "Measurement interval is 10 seconds.";
      }
      enum "30s" {
        value 2;
        description
          "Measurement interval is 30 seconds.";
      }
      enum "60s" {
        value 3;
        description
          "Measurement interval is 60 seconds.";
      }
      enum "300s" {
        value 4;
        description
          "Measurement interval is 300 seconds.";
      }	  
    }
    description
      "Measure interval.";
  }
  typedef inst-type {
    type enumeration {
      enum "instance" {
        value 0;
        description
          "Instance type.";
      }
      enum "instance-ht16" {
        value 2;
        description
          "Header type 16 instance.";
      }
    }
    description
      "Instance type.";
  }
  typedef operate-color-flag-type {
    type enumeration {
      enum "keep" {
        value 1;
        description
          "Keep color flag.";
      }
      enum "clear" {
        value 2;
        description
          "Clear color flag.";
      }
    }
    description
      "Type of operating color flag.";
  }
  typedef extend-mode-type {
    type enumeration {
      enum "base-l3vpn" {
        value 0;
        description
          "Support IFIT for L3VPN.";
      }
      enum "extend-l2vpn" {
        value 1;
        description
          "Support IFIT for L2VPN.";
      }
    }
    description
      "Extended mode type.";
  }
  typedef flow-scenario {
    type enumeration {
      enum "flow-apn" {
        value 1;
        description
          "Scenario of IFIT APN flow.";
      }
      enum "flow-evpn" {
        value 2;
        description
          "Scenario of IFIT EVPN flow.";
      }
    }
    description
      "Scenario of an IFIT flow.";
  }
  typedef leap-mode-type {
    type enumeration {
      enum "leap59" {
        value 1;
        description
          "The leap second is set to 59 seconds.";
      }
      enum "leap61" {
        value 2;
        description
          "The leap second is set to 61 seconds.";
      }
    }
    description
      "Type of leap mode.";
  }
  grouping bind-ifs-grp {
    description
      "List of flow specified interfaces of IFIT.";
    container bind-ifs {
      description
        "List of flow specified interfaces of IFIT.";
      list bind-if {
        key "if-name";
        description
          "Configure flow specified interface of IFIT.";
        leaf if-name {
          type leafref {
            path "/ifm:ifm/ifm:interfaces/ifm:interface/ifm:name";
          }
          description
            "Interface name to which an IFIT flow binds.";
        }
        leaf flow-id {
          type uint64;
          config false;
          description
            "Flow ID of an IFIT flow.";
        }
      }
    }
  }

  rpc reset-dynamic-flow-all {
    description
      "Clear all dynamic IFIT flow.";
    ext:node-ref "/ifit:ifit/ifit-common:ifit-common/ifit-common:dynamic-flow-hops";
    input {
      leaf all-flow {
        type boolean;
        mandatory true;
        description
          "Clear all dynamic IFIT flow.";
      }
    }
  }
  rpc reset-dynamic-flowid {
    description
      "Clear specified dynamic IFIT ID.";
    ext:node-ref "/ifit:ifit/ifit-common:ifit-common/ifit-common:dynamic-flow-hops/ifit-common:dynamic-flow-hop";
    input {
      leaf flow-id {
        type uint64;
        mandatory true;
        description
          "Clear specified dynamic IFIT ID.";
      }
    }
  }
  rpc set-dynamic-flow {
    description
      "Set IFIT Flow parameter.";
    ext:node-ref "/ifit:ifit/ifit-common:ifit-common/ifit-common:dynamic-flows/ifit-common:dynamic-flow";
    input { 
      leaf source-ip {
        type inet:ip-address-no-zone;
        description
          "Source IP address of an IFIT flow.";
      }
      leaf destination-ip {
        type inet:ip-address-no-zone;
        description
          "Destination IP address of an IFIT flow.";
      }
      leaf source-mask {
        when "../source-ip";
        type uint8;
        description
          "Source IP address mask of an IFIT flow.";
      }
      leaf destination-mask {
        when "../destination-ip";
        type uint8;
        description
         "Destination IP address mask of an IFIT flow.";
      }
      leaf address-type {
        type ifit-common:addr-type;
        mandatory true;
        description
          "Address type of IFIT flow.";
      }	
      leaf if-name {
        type leafref {
          path "/ifm:ifm/ifm:interfaces/ifm:interface/ifm:name";
        }
        mandatory true;
        description
          "Interface name to which an IFIT flow binds.";
      }  
      leaf ni-name {
        type leafref {
          path "/ni:network-instance/ni:instances/ni:instance/ni:name";
        }
        description
          "Name of the VPN to which an IFIT flow belongs.";
      }
      leaf dscp {
        type uint16 {
          range "0..63";
        }
        description
          "DSCP of an IFIT flow.";
      }
      leaf interval {
        type uint16 {
          range "10|30|60|300";
        }
        units "s";
        default "30";
        description
          "Interval of an IFIT flow.";
      }
      leaf measure-mode {
        type ifit-common:measure-mode;
        default "e2e";
        description
          "Measure mode of an IFIT flow.";
        }
      leaf loss-measure-enable {
        type boolean;
        default "true";
        description
            "Enable/disable loss measure function of an IFIT flow.";
      }
      leaf delay-measure-enable {
        type boolean;
        default "true";
        description
          "Enable/disable delay measure function of an IFIT flow.";
      }
      leaf disorder-measure-enable {
        type boolean;
        default "false";
        description
          "Enable/disable disorder measure function of an IFIT flow.";
      }
      leaf protocol {
        type uint8 {
          range "0..254";
          ext:value-meaning {
            ext:item  "6" {
              ext:meaning "tcp";
            }
            ext:item  "17" {
              ext:meaning "udp";
            }
            ext:item  "132" {
              ext:meaning "sctp";
            }
          }
        }
        description
          "Protocol of an IFIT flow.";
      }
      leaf source-port {
        type uint16 {
          range "1..65535";
        }
        description
          "Source port of an IFIT flow.";
      }
      leaf destination-port {
        type uint16 {
          range "1..65535";
        }
        description
          "Destination port of an IFIT flow.";
      }
      leaf delay-per-packet-enable {
        type boolean;
        default "false";
        description
         "Enable/disable delay per-packet function of an IFIT flow.";
          }
    }
  }
  rpc reset-dynamic-flow {
    description
      "Clear specified dynamic flow.";
    ext:node-ref "/ifit:ifit/ifit-common:ifit-common/ifit-common:dynamic-flows/ifit-common:dynamic-flow";
    input { 
      leaf address-type {
        type ifit-common:addr-type;
        mandatory true;
        description
          "Address type of IFIT flow.";
      }
      leaf source-ip {
        type inet:ip-address-no-zone;
        description
          "Source IP address of an IFIT flow.";
      }
      leaf destination-ip {
        type inet:ip-address-no-zone;
        description
          "Destination IP address of an IFIT flow.";
      }
      leaf source-mask {
        when "../source-ip";
        type uint8 {
          range "1..128";
        }
        description
          "Source IP address mask of an IFIT flow.";
      }
      leaf destination-mask {
        when "../destination-ip";
        type uint8 {
          range "1..128";
        }
        description
         "Destination IP address mask of an IFIT flow.";
      }
      leaf protocol {
        type uint8 {
          range "0..254";
          ext:value-meaning {
            ext:item  "6" {
              ext:meaning "tcp";
            }
            ext:item  "17" {
              ext:meaning "udp";
            }
            ext:item  "132" {
              ext:meaning "sctp";
            }
          }
        }
        description
          "Protocol of an IFIT flow.";
      }
      leaf source-port {
        type uint16 {
          range "1..65535";
        }
        description
          "Source port of an IFIT flow.";
      }
      leaf destination-port {
        type uint16 {
          range "1..65535";
        }
        description
          "Destination port of an IFIT flow.";
      }
      leaf ni-name {
        type leafref {
          path "/ni:network-instance/ni:instances/ni:instance/ni:name";
        }
        description
          "Name of the VPN to which an IFIT flow belongs.";
      }
      leaf if-name {
        type leafref {
          path "/ifm:ifm/ifm:interfaces/ifm:interface/ifm:name";
        }
        mandatory true;
        description
          "Interface name to which an IFIT flow binds.";
      }
      leaf dscp {
        type uint16 {
          range "0..63";
        }
        description
          "DSCP of an IFIT flow.";
      }
    }
  }
  augment "/ifit:ifit" {
    description
      "The IFIT augment.";
    container ifit-common {
      description
        "Configure IFIT function.";
      container global {
        description
          "Configure global parameter of IFIT.";
        leaf node-id {
          ext:operation-exclude update {
            when "../../static-instances/static-instance";
            description "The 'node-id' cannot be updated, when static-instance exists.";
          }
          type uint32 {
            range "1..1048575";
          }
          description
            "Node ID of IFIT.";
        }
        leaf dynamic-flow-aging-multiplier  {
            type uint16 {
              range "2..100";
            }
            description
              "Multiplier of an dynamic IFIT flow age interval. If the instance interval calculation result is less than 10 minutes, the 10 minutes shall prevail.";
        }
        leaf clock-mode {
          ext:operation-exclude update|delete {
            when "../../static-instances/static-instance";
            description "The 'clock-mode' cannot be updated or deleted, when static-instance exists.";
          }
          type clock-mode-type;
          must "../clock-mode='common' or (../clock-mode='precision-sampling' and count(../../static-instances/static-instance)<=1024) or (../clock-mode='precision-full' and count(../../static-instances/static-instance)<=1)";
          default "common";
          description
            "Clock mode of IFIT.";
        }
        leaf measure-enable {
          type boolean;
	      default "true";
          description
            "Enable/disable measure function of IFIT.";
        }
        choice period-clock-mode {
          default "ntp";
          description
            "The period clock mode used to calculate IFIT interval.";
          case ntp {
            description
              "The NTP mode.";
            leaf ntp {
              type empty;
              description
                "The NTP mode.";
 
            }
          }
          case ptp {
            description
              "The PTP mode.";
            leaf ptp-utc-offset {
              type uint8 {
                range "1..255";
              }
              mandatory true;
              description
                "The offset between PTP and NTP.";
            }
            leaf leap-mode {
              type leap-mode-type;
              description
                "The method of leap second adjustment.";
            }
            leaf preset-date {
              when "../leap-mode";
              type pub-type:date;
              mandatory true;
              description
                "The preset date of leap second adjustment.";
            }
          }
        }
      }
      container next-hops {
        description
          "List of IFIT function for the next hop addresses.";
        list next-hop {
          key "address";
          description
            "Configure IFIT function for the next hop address.";
          leaf address {
            type inet:ip-address-no-zone;
            description
              "Next hop address.";
          }
          leaf extend-mode {
            type extend-mode-type;
            default "base-l3vpn";
            description
              "Extended IFIT capability.";
          }
        }
      }
      container peer-locators {
        description
          "List of IFIT function for the next locator addresses.";
        list peer-locator {
          key "prefix";
          status obsolete;
          description
            "Configure IFIT function for the next locator address.";
          leaf prefix {
            type inet:ipv6-address-no-zone;
            status obsolete;
            description
              "Next locator address.";
          }
          leaf prefix-mask-length {
            ext:operation-exclude update;
            type uint32 {
              range "32..120";
            }
            mandatory true;
            status obsolete;
            description
              "Mask length of a next locator address.";
          }
        }
      }
      container static-instances {
        description
          "List of static instances of IFIT.";
        list static-instance {
          must "gtpu-sn-measure-enable='false' or disorder-measure-enable = 'false'";
          must "../../global/clock-mode='common' or (disorder-measure-enable='false' and gtpu-sn-measure-enable='false')";
          must "delay-per-packet-enable = 'false' or (loss-measure-enable = 'true' and disorder-measure-enable = 'false' and gtpu-sn-measure-enable = 'false')";
          key "name";
          unique "flow/flow-filter/filter-condition1/flow-address-type/ipv4-condition/source-ip flow/flow-filter/filter-condition1/flow-address-type/ipv4-condition/destination-ip flow/flow-filter/filter-condition1/flow-address-type/ipv4-condition/source-mask flow/flow-filter/filter-condition1/flow-address-type/ipv4-condition/destination-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition1/flow-address-type/ipv6-condition/source-ipv6 flow/flow-filter/filter-condition1/flow-address-type/ipv6-condition/destination-ipv6 flow/flow-filter/filter-condition1/flow-address-type/ipv6-condition/source-ipv6-mask flow/flow-filter/filter-condition1/flow-address-type/ipv6-condition/destination-ipv6-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition2/vpn-filter/ni-condition/address-type flow/flow-filter/filter-condition2/vpn-filter/ni-condition/peer-ni-name flow/flow-filter/filter-condition2/peer-filter/ip-condition/peer-ip";
          unique "flow/flow-filter/filter-condition2/vpn-filter/evpl-condition/peer-evpl-id flow/flow-filter/filter-condition2/peer-filter/ip-condition/peer-ip";
          description
            "Configure static instance of IFIT.";
          leaf name {
            type string {
              length "1..31";
            }
            must "(../../../global/node-id)";
            description
              "Instance name of IFIT.";
          }
          leaf interval {
            type uint16 {
              range "10|30|60|300";
            }
            units "s";
            default "30";
            description
              "Interval of an IFIT flow.";
          }
          leaf measure-mode {
            type ifit-common:measure-mode;
            default "e2e";
            description
              "Measure mode of an IFIT flow.";
          }
          leaf loss-measure-enable {
            type boolean;
            default "true";
            description
              "Enable/disable loss measure function of an IFIT flow.";
          }
          leaf delay-measure-enable {
            type boolean;
            default "true";
            description
              "Enable/disable delay measure function of an IFIT flow.";
          }
          leaf disorder-measure-enable {
            type boolean;
            default "false";
            description
              "Enable/disable disorder measure function of an IFIT flow.";
          }
          leaf gtpu-sn-measure-enable {
            type boolean;
            default "false";
            description
              "Enable/disable gtpu sequence number measure function of an IFIT flow.";
          }
          leaf delay-per-packet-enable {
            type boolean;
            default "false";
            description
              "Enable/disable delay per-packet function of an IFIT flow.";
          }
          leaf single-device-measure-enable {
            type boolean;
            default "false";
            description
              "Enable/disable single device measure function of an IFIT flow.";
          }
          leaf flow-scenario {
            type flow-scenario;
            description
              "Scenario of an IFIT flow.";
          }
          container flow {
            must "not (../flow-scenario)";
            must "flow-type='bidirection' or (source-ip or source-ipv6 or address-type or peer-evpl-id)";
            must "not (gtp-enable='true') or (not (protocol) or (protocol='17' and ((source-port=2152 and destination-port>=2152) or (destination-port=2152 and source-port>=2152))))";
            must "../../../global/clock-mode='common' or (not(address-type) and not(peer-evpl-id) and not(peer-ip) and not(peer-locator-prefix))";
            must "../../../global/clock-mode!='precision-full' or ../interval=10";
            presence "Enable flow";
            description
              "Configure IFIT flow.";
            leaf flow-type {
              ext:operation-exclude update;
              type ifit-common:flow-type;
              must "../../../../global/clock-mode='common' or ../flow-type='unidirection'";
              must "(../../single-device-measure-enable='true' and ../flow-type='unidirection') or (../../single-device-measure-enable='false')";
              mandatory true;
              description
                "Flow type of an IFIT flow.";
            }
            choice flow-filter {
              mandatory true;
              description
                "Configure the filter of a flow.";
              case filter-condition1{
                description
                  "Filter condition 1.";
                choice flow-address-type {
                  mandatory true;
                  description
                    "Configure the address of a flow.";
                    case ipv4-condition{
                      description
                      "IPv4 condition.";
                      leaf source-ip {
                        ext:operation-exclude update|delete;
                        ext:support-filter "true";
                        type inet:ipv4-address-no-zone;
                        description
                          "Source IPv4 address of an IFIT flow.";
                      }
                      leaf destination-ip {
                        ext:operation-exclude update;
                        ext:support-filter "true";
                        type inet:ipv4-address-no-zone;
                        must "../destination-ip != ../source-ip";
                        mandatory true;
                        description
                          "Destination IPv4 address of an IFIT flow.";
                      }
                      leaf source-mask {
                        when "../source-ip";
                        ext:operation-exclude update|delete;
                        type uint8 {
                          range "1..32";
                        }
                        default "32";
                        description
                        "Source IPv4 address mask of an IFIT flow.";
                      }
                      leaf destination-mask {
                        ext:operation-exclude update|delete;
                        type uint8 {
                          range "1..32";
                        }
                        default "32";
                        description
                          "Destination IPv4 address mask of an IFIT flow.";
                      }
                    }
                    case ipv6-condition{
                      description
                      "IPv6 condition.";
                      leaf source-ipv6 {
                        ext:operation-exclude update;
                        ext:support-filter "true";
                        type inet:ipv6-address-no-zone;
                        mandatory true;
                        description
                          "Source IPv6 address of an IFIT flow.";
                      }
                      leaf destination-ipv6 {
                        ext:operation-exclude update;
                        ext:support-filter "true";
                        type inet:ipv6-address-no-zone;
                        must "../destination-ipv6 != ../source-ipv6";
                        mandatory true;
                        description
                          "Destination IPv6 address of an IFIT flow.";
                      }
                      leaf source-ipv6-mask {
                        ext:operation-exclude update|delete;
                        type uint8 {
                          range "32..128";
                        }
                        default "128";
                        description
                        "Source IPv6 address mask of an IFIT flow.";
                      }
                      leaf destination-ipv6-mask {
                        ext:operation-exclude update|delete;
                        type uint8 {
                          range "32..128";
                        }
                        default "128";
                        description
                          "Destination IPv6 address mask of an IFIT flow.";
                      }
                    }
                }
                leaf protocol {
                  ext:operation-exclude update|delete;
                  type uint8 {
                    range "0..254";
                    ext:value-meaning {
                      ext:item  "6" {
                        ext:meaning "tcp";
                      }
                      ext:item  "17" {
                        ext:meaning "udp";
                      }
                      ext:item  "132" {
                        ext:meaning "sctp";
                      }
                    }
                  }
                  description
                    "Protocol of an IFIT flow.";
                }
                leaf source-port {
                  ext:operation-exclude update|delete;
                  type uint16 {
                    range "1..65535";
                  }
                  must "../protocol=6 or ../protocol=17 or ../protocol=132";
                  description
                    "Source port of an IFIT flow.";
                }
                leaf destination-port {
                  ext:operation-exclude update|delete;
                  type uint16 {
                    range "1..65535";
                  }
                  must "../protocol =6 or ../protocol=17 or ../protocol=132";
                  description
                    "Destination port of an IFIT flow.";
                }
                leaf gtp-enable {
                  when "../flow-type='unidirection'";
                  ext:operation-exclude update|delete;
                  type boolean;
                  default "false";
                  description
                    "Enable/disable GTP protocol measure for an IFIT flow.";
                }
                leaf gtp-teid {
                  when "../flow-type='unidirection' and ../gtp-enable = 'true'";
                  ext:operation-exclude update|delete;
                  type uint32 {
                    range "1..4294967295";
                  }
                  description
                    "GTP TEID of an IFIT flow.";
                }
                leaf ni-name {
                  ext:operation-exclude update|delete;
                  type leafref {
                    path "/ni:network-instance/ni:instances/ni:instance/ni:name";
                  }
                  must "../ni-name!='_public_' and (((../destination-ip) and /ni:network-instance/ni:instances/ni:instance[ni:name=current()]/l3vpn:afs/l3vpn:af[l3vpn:type='ipv4-unicast']) or ((../destination-ipv6) and /ni:network-instance/ni:instances/ni:instance[ni:name=current()]/l3vpn:afs/l3vpn:af[l3vpn:type='ipv6-unicast']))";
                  description
                    "Name of the VPN to which an IFIT flow belongs.";
                }
                leaf dscp {
                  ext:operation-exclude update|delete;
                  type uint16 {
                    range "0..63";
                  }
                  description
                    "DSCP of an IFIT flow.";
                }
              }
              case filter-condition2{
                when "flow-type='unidirection' and ../gtpu-sn-measure-enable='false'";
                description
                  "Filter condition 2.";
                choice vpn-filter {
                  mandatory true;
                  description
                    "Configure the VPN filter of a flow.";
                  case ni-condition {
                    description
                      "Peer netconf instance condition.";
                    leaf address-type {
                      ext:operation-exclude update;
                      type addr-family-type;
                      mandatory true;
                      description
                        "Address type of an IFIT flow peer.";
                    }
                    leaf peer-ni-name {
                      ext:operation-exclude update|delete;
                      type leafref {
                        path "/ni:network-instance/ni:instances/ni:instance/ni:name";
                      }
                      must " ../peer-ni-name!='_public_' and /ni:network-instance/ni:instances/ni:instance[ni:name = current()]/l3vpn:afs/l3vpn:af[l3vpn:type=current()/../address-type]";
                      description
                        "Name of the VPN to which an IFIT flow peer belongs.";
                    }
                  }
                  case evpl-condition {
                    description
                      "Peer EVPL condition.";
                    leaf peer-evpl-id {
                      ext:operation-exclude update;
                      type leafref {
                        path "/evpl:evpl/evpl:instances/evpl:instance/evpl:id";
                      }
                      must "((../peer-ip and /evpl:evpl/evpl:instances/evpl:instance[evpl:id=current()][evpl:mode!='vxlan-mode']) or (../peer-locator-prefix and /evpl:evpl/evpl:instances/evpl:instance[evpl:id=current()][evpl:mode!='vxlan-mode']))";
                      must "../../single-device-measure-enable='false'";
                      mandatory true;
                      description
                        "ID of the EVPL instance to which an IFIT flow peer belongs.";
                    }
                  }
                }
                choice peer-filter {
                  mandatory true;
                  description
                    "Configure the peer filter of a flow.";
                  case ip-condition {
                    description
                      "Peer filter ip condition.";
                    leaf peer-ip {
                    ext:operation-exclude update;
                    type inet:ipv4-address-no-zone;
                    must "../peer-ni-name or ../peer-evpl-id";
                    mandatory true;
                    description
                      "Peer IP address of an IFIT flow.";
                    }
                  }
                  case locator-condition {
                    description
                      "Peer filter locatior condition.";
                    leaf peer-locator-prefix {
                      ext:operation-exclude update;
                      type inet:ipv6-address-no-zone;
                      mandatory true;
                      description
                        "Peer locator address.";
                    }
                    leaf peer-locator-prefix-mask-len {
                      ext:operation-exclude update;
                      type uint32 {
                        range "32..120";
                      }
                      mandatory true;
                      description
                        "Mask length of a peer locator address.";
                    }
                  }
                }
              }
            }
            uses bind-ifs-grp;
          }
          container flow-evpn {
            when "../gtpu-sn-measure-enable='false' and ../flow-scenario='flow-evpn'";
            must "../single-device-measure-enable='false'";
            presence "Enable EVPN flow";
            description
              "Configure IFIT EVPN flow.";
            leaf evpn-name {
              type leafref {
                path "/evpn:evpn/evpn:instances/evpn:instance/evpn:name";
              }
              must "(/evpn:evpn/evpn:instances/evpn:instance[evpn:name=current()]/evpn:type='normal' and not(../bd-id)) or (/evpn:evpn/evpn:instances/evpn:instance[evpn:name=current()]/evpn:type='bd-evpn' and ../bd-id)";
              mandatory true;
              description
                "EVPN name of an IFIT flow.";
            }
            leaf bd-id {
              type leafref {
                path "/bd:bd/bd:instances/bd:instance/bd:id";
              }
              must "/bd:bd/bd:instances/bd:instance[bd:id=current()]/evpn:evpn[evpn:name=current()/../evpn-name]";
              description
                "ID of the Bridge Domain to which an IFIT flow belongs.";
            }
            choice evpn-filter {
              mandatory true;
              description
                "Configure the EVPN filter of a flow.";
              case ip-condition {
                description
                  "Peer filter IP condition.";
                leaf evpn-peer-ip {
                  ext:support-filter "true";
                  type inet:ipv4-address-no-zone;
                  mandatory true;
                  description
                    "Peer IP address of an IFIT flow.";
                }
              }
              case locator-condition {
                description
                  "Peer filter locator condition.";
                leaf evpn-peer-locator-prefix {
                  ext:support-filter "true";
                  type inet:ipv6-address-no-zone;
                  mandatory true;
                  description
                    "Peer locator address of an IFIT flow.";
                }
                leaf evpn-peer-locator-prefix-mask-len {
                  type uint32 {
                    range "32..120";
                  }
                  mandatory true;
                  description
                    "Mask length of a peer locator address.";
                }
              }
              case mac-condition {
                description
                  "Peer filter MAC condition.";
                leaf source-mac-address {
                  ext:support-filter "true";
                  type pub-type:mac-address;
                  description
                    "Source MAC address of an IFIT flow.";
                }
                leaf destination-mac-address {
                  ext:support-filter "true";
                  type pub-type:mac-address;
                  must "../destination-mac-address != ../source-mac-address";
                  description
                    "Destination MAC address of an IFIT flow.";
                }
                leaf eth-type {
                  ext:support-filter "true";
                  type pub-type:hex-binary {
                    length "1..6";
                  }
                  must "../eth-type != '0x0'";
                  description
                    "Ethernet type of an IFIT flow.";
                }
              }
            }
            uses bind-ifs-grp;
          }
          container flow-apn {
            when "../gtpu-sn-measure-enable='false' and ../flow-scenario='flow-apn'";
            must "../single-device-measure-enable='false'";
            presence "Enable APN flow";
            description
              "Configure IFIT APN flow.";
            leaf apn-inst-name {
              type leafref {
                path "/apn:apn/apn:ipv6/apn:apn-id-instances/apn:apn-id-instance/apn:name";
              }
              mandatory true;
              description
                "APN ID IPv6 instance name.";
            }
            uses bind-ifs-grp;
          }
        }
      }
      container instance-ht16s {
        description
          "List of instances of IFIT, whose alternate marking header type value is 16.";
        list instance-ht16 {
          key "name";
          unique "flow/flow-filter/filter-condition1/flow-address-type/ipv4-condition/source-ip flow/flow-filter/filter-condition1/flow-address-type/ipv4-condition/destination-ip flow/flow-filter/filter-condition1/flow-address-type/ipv4-condition/source-mask flow/flow-filter/filter-condition1/flow-address-type/ipv4-condition/destination-mask flow/flow-filter/filter-condition1/protocol flow/flow-filter/filter-condition1/source-port flow/flow-filter/filter-condition1/destination-port flow/flow-filter/filter-condition1/ni-name flow/flow-filter/filter-condition1/dscp";
          unique "flow/flow-filter/filter-condition1/flow-address-type/ipv6-condition/source-ipv6 flow/flow-filter/filter-condition1/flow-address-type/ipv6-condition/destination-ipv6 flow/flow-filter/filter-condition1/flow-address-type/ipv6-condition/source-ipv6-mask flow/flow-filter/filter-condition1/flow-address-type/ipv6-condition/destination-ipv6-mask flow/flow-filter/filter-condition1/protocol flow/flow-filter/filter-condition1/source-port flow/flow-filter/filter-condition1/destination-port flow/flow-filter/filter-condition1/ni-name flow/flow-filter/filter-condition1/dscp";          
          description
            "Configure IFIT instance.";
          leaf name {
            type string {
              length "1..31";
            }
            must "(../../../global/node-id)";
            description
              "Instance name of IFIT.";
          }
          leaf interval {
            type interval-type;
            default "30s";
            description
              "Interval of an IFIT flow.";
          }
          leaf measure-mode {
            type measure-mode;
            default "e2e";
            description
              "Measure mode of an IFIT flow.";
          }
          leaf measure-enable {
            type boolean;
            default "true";
            description
              "Enable/disable measure function of an IFIT flow.";
          }
          leaf delay-measure-enable {
            type boolean;
            default "false";
            description
              "Enable/disable delay measure function of an IFIT flow.";
          }
          container flow {
            presence "Enable flow of the instance";
            description
              "Configure IFIT flow of the instance.";
            leaf flow-type {
              type flow-type;
              mandatory true;
              description
                "Flow type of an IFIT flow.";
            }
            choice flow-filter {
              mandatory true;
              description
                "Configure the filter of an IFIT flow.";
              case filter-condition1 {
                description
                  "Filter condition 1.";
                leaf address-family {
                  type addr-type;
                  mandatory true;
                  description
                    "Address type of an IFIT flow.";				  
                }
                choice flow-address-type {
                  description
                    "Configure the address of an IFIT flow.";
                  case ipv4-condition{
                    when "address-family='ipv4'";
                    description
                      "IPv4 condition.";
                    leaf source-ip {
                      ext:support-filter "true";
                      type inet:ipv4-address-no-zone;
                      description
                        "Source IPv4 address of an IFIT flow.";
                    }
                    leaf destination-ip {
                      ext:support-filter "true";
                      type inet:ipv4-address-no-zone;
                      must "../destination-ip != ../source-ip";
                      description
                        "Destination IPv4 address of an IFIT flow.";
                    }
                    leaf source-mask {
                      when "../source-ip";
                      type uint8 {
                        range "1..32";
                      }
                      default "32";
                      description
                        "Source IPv4 address mask of an IFIT flow.";
                    }
                    leaf destination-mask {
                      when "../destination-ip";
                      type uint8 {
                        range "1..32";
                      }
                      default "32";
                      description
                        "Destination IPv4 address mask of an IFIT flow.";
                    }
                  }
                  case ipv6-condition{
                    when "address-family='ipv6'";				  
                    description
                      "IPv6 condition.";
                    leaf source-ipv6 {
                      ext:support-filter "true";
                      type inet:ipv6-address-no-zone;
                      description
                        "Source IPv6 address of an IFIT flow.";
                    }
                    leaf destination-ipv6 {
                      ext:support-filter "true";
                      type inet:ipv6-address-no-zone;
                      must "../destination-ipv6 != ../source-ipv6";
                      description
                        "Destination IPv6 address of an IFIT flow.";
                    }
                    leaf source-ipv6-mask {
                      when "../source-ipv6";
                      type uint8 {
                        range "1..128";
                      }
                      default "128";
                      description
                        "Source IPv6 address mask of an IFIT flow.";
                    }
                    leaf destination-ipv6-mask {
                      when "../destination-ipv6";
                      type uint8 {
                        range "1..128";
                      }
                      default "128";
                      description
                        "Destination IPv6 address mask of an IFIT flow.";
                    }
                  }
                }
                leaf protocol {
                  type uint8 {
                    range "0..255";
                    ext:value-meaning {
                      ext:item  "6" {
                        ext:meaning "tcp";
                      }
                      ext:item  "17" {
                        ext:meaning "udp";
                      }
                      ext:item  "132" {
                        ext:meaning "sctp";
                      }
                    }
                  }
                  description
                    "Protocol of an IFIT flow.";
                }
                leaf source-port {
                  type uint16 {
                    range "0..65535";
                  }
                  must "../source-port=0 or (../protocol=6 or ../protocol=17 or ../protocol=132)";
                  default "0";
                  description
                    "Source port of an IFIT flow.";
                }
                leaf destination-port {
                  type uint16 {
                    range "0..65535";
                  }
                  must "../destination-port=0 or (../protocol=6 or ../protocol=17 or ../protocol=132)";
                  default "0";
                  description
                    "Destination port of an IFIT flow.";
                }
                leaf ni-name {
                  type leafref {
                    path "/ni:network-instance/ni:instances/ni:instance/ni:name";
                  }
                  must "../ni-name!='_public_' and ((../address-family='ipv4' and /ni:network-instance/ni:instances/ni:instance[ni:name=current()]/l3vpn:afs/l3vpn:af[l3vpn:type='ipv4-unicast']) or (../address-family='ipv6' and /ni:network-instance/ni:instances/ni:instance[ni:name=current()]/l3vpn:afs/l3vpn:af[l3vpn:type='ipv6-unicast']))"; 
                  description
                    "Name of the VPN to which an IFIT flow belongs.";
                }
                leaf dscp {
                  type uint16 {
                    range "0..63";
                  }
                  description
                    "DSCP of an IFIT flow.";
                }
              }
            }
            container bind-ifs {
              description
                "List of flow specified interfaces of IFIT.";
              list bind-if {
                key "if-name";
                description
                  "Configure flow specified interface of IFIT.";
                leaf if-name {
                  type leafref {
                    path "/ifm:ifm/ifm:interfaces/ifm:interface/ifm:name";
                  }
                  description
                    "Interface name to which an IFIT flow binds.";
                }
                leaf flow-id {
                  type uint64;
                  config false;
                  description
                    "Flow ID of an IFIT flow.";
                }
                leaf flow-monitor-id {
                  type uint32;
                  config false;
                  description
                    "Flow monitor ID of an IFIT flow, which is part of the flow ID and unique within a device.";
                }
                leaf measure-state {
                  type boolean;
                  default "true";
                  config false;
                  description
                    "Enable/disable measure function of an IFIT flow.";
                }
              }
            }
          }
        }
      }	  
      container dynamic-flow-hops {
        config false;
        description
          "List of dynamic flow hops of IFIT.";
        list dynamic-flow-hop {
          key "flow-id if-name direction";
          description
            "Operational data of dynamic flow hop of IFIT.";
          leaf flow-id {
            type uint64;
            description
              "Flow ID of an IFIT flow.";
          }
          leaf if-name {
            type leafref {
              path "/ifm:ifm/ifm:interfaces/ifm:interface/ifm:name";
            }
            description
              "Interface name to which an IFIT flow passes.";
          }
          leaf direction {
            type ifit-common:flow-direction;
            description
              "Direction of an IFIT flow.";
          }
          leaf flow-monitor-id {
            type uint32;
            description
              "Flow monitor ID of an IFIT flow, which is part of the flow ID and unique within a device.";
          }
          leaf node-id {
            type uint32;
            description
              "Node ID of IFIT.";
          }
          leaf instance-type {
            type inst-type;
            description
              "Instance type of an IFIT flow.";
          }
          leaf flow-type {
            type ifit-common:flow-type;
            description
              "Flow type of an IFIT flow.";
          }
          leaf interval {
            type uint16 {
              range "1|2|10|30|60|300";
            }
            units "s";
            description
              "Interval of an IFIT flow.";
          }
          leaf loss-measure-enable {
            type boolean;
            description
              "Enable/disable loss measure function of an IFIT flow.";
          }
          leaf delay-measure-enable {
            type boolean;
            description
              "Enable/disable delay measure function of an IFIT flow.";
          }
          leaf disorder-measure-enable {
            type boolean;
            description
              "Enable/disable disorder measure function of an IFIT flow.";
          }
        }
      }
      container dynamic-flows {
        config false;
        description
          "List of dynamic flows of IFIT.";
        list dynamic-flow {
          key "flow-id";
          description
            "Operational data of dynamic flow of IFIT.";
          leaf flow-id {
            type uint64;
            description
              "Flow ID of an IFIT flow.";
          }
          leaf flow-type {
            type ifit-common:flow-type;
            description
              "Flow type of an IFIT flow.";
          }
          leaf address-type {
              type addr-type;
              description
                "Address type of an IFIT flow.";
          }
          leaf source-ip {
            ext:support-filter "true";
            type inet:ip-address-no-zone;
            description
              "Source IP address of an IFIT flow.";
          }
          leaf destination-ip {
            ext:support-filter "true";
            type inet:ip-address-no-zone;
            description
              "Destination IP address of an IFIT flow.";
          }
          leaf source-mask {
            type uint8 {
              range "1..128";
            }
            description
              "Source IP address mask of an IFIT flow.";
          }
          leaf destination-mask {
            type uint8 {
              range "1..128";
            }
            description
              "Destination IP address mask of an IFIT flow.";
          }
          leaf protocol {
            type uint8 {
              range "0..254";
              ext:value-meaning {
                ext:item  "6" {
                  ext:meaning "tcp";
                }
                ext:item  "17" {
                  ext:meaning "udp";
                }
                ext:item  "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
          leaf ni-name {
            type leafref {
              path "/ni:network-instance/ni:instances/ni:instance/ni:name";
            }
            description
              "Name of the VPN to which an IFIT flow belongs.";
          }
          leaf if-name {
            type leafref {
              path "/ifm:ifm/ifm:interfaces/ifm:interface/ifm:name";
            }
            description
              "Interface name to which an IFIT flow passes.";
          }
          leaf interval {
            type uint16 {
              range "10|30|60|300";
            }
            units "s";
            description
              "Interval of an IFIT flow.";
          }
          leaf measure-mode {
            type ifit-common:measure-mode;
            description
              "Measure mode of an IFIT flow.";
          }
          leaf delay-measure-enable {
            type boolean;
            description
              "Enable/disable delay measure function of an IFIT flow.";
          }
          leaf loss-measure-enable {
            type boolean;
            description
              "Enable/disable loss measure function of an IFIT flow.";
          }
          leaf disorder-measure-enable {
            type boolean;
            description
              "Enable/disable disorder measure function of an IFIT flow.";
          }
          leaf dscp {
            type uint16 {
              range "0..63";
            }
            description
              "DSCP of an IFIT flow.";
          }
          leaf delay-per-packet-enable {
            type boolean;
            description
              "Enable/disable delay per-packet function of an IFIT flow.";
          }
        }
      }
      container whitelist-groups {
        description
          "List of whitelist groups of IFIT.";
        list whitelist-group {
          key "group-name";
          description
            "Configure whitelist group of IFIT.";
          leaf group-name {
            type string {
              length "1..31";
            }
            description
              "Whitelist group name.";
          }
          leaf mode {
            type whitelist-group-mode;
            default "native-ip";
            description
              "Whitelist group mode.";
          }
          container whitelist-rules {
            description
              "List of whitelist rules of IFIT.";
            list whitelist-rule {
              ext:operation-exclude update;
              must "source-ipv4-address or source-ipv4-mask or destination-ipv4-address or destination-ipv4-mask or source-ipv6-address or source-ipv6-mask or destination-ipv6-address or destination-ipv6-mask or protocol";
              key "rule-name";
              description
                "Configure whitelist rule of IFIT.";
              leaf rule-name {
                type string {
                  length "1..31";
                }
                description
                  "Whitelist rule name.";
              }
              leaf address-family {
                type ifit-common:addr-type;
                mandatory true;
                description
                  "Address family type of an IFIT whitelist rule.";
              }
              choice address-type {
                description
                  "Configure the address of an IFIT whitelist rule.";
                case ipv4-condition{
                  when "address-family='ipv4'";
                  description
                    "IPv4 condition.";
                  leaf source-ipv4-address {
                    type inet:ipv4-address-no-zone;
                    description
                      "Source IPv4 address.";
                  }
                  leaf source-ipv4-mask {
                    type uint8 {
                      range "1..32";
                    }
                    ext:dynamic-default {
                      ext:default-value "32" {
                        when "../source-ipv4-address";
                        description "The default value is 32 when source IPv4 address is configured.";
                      }
                    }
                    description
                      "Source IPv4 address mask.";
                  }
                  leaf destination-ipv4-address {
                    type inet:ipv4-address-no-zone;
                    description
                      "Destination IPv4 address.";
                  }
                  leaf destination-ipv4-mask {
                    type uint8 {
                      range "1..32";
                    }
                    ext:dynamic-default {
                      ext:default-value "32" {
                        when "../destination-ipv4-address";
                        description "The default value is 32 when destination IPv4 address is configured.";
                      }
                    }
                    description
                      "Destination IPv4 address mask.";
                  }
                }
                case ipv6-condition{
                  when "address-family='ipv6'";
                  description
                    "IPv6 condition.";
                  leaf source-ipv6-address {
                    type inet:ipv6-address-no-zone;
                    description
                      "Source IPv6 address.";
                  }
                  leaf source-ipv6-mask {
                    type uint8 {
                      range "1..128";
                    }
                    ext:dynamic-default {
                      ext:default-value "128" {
                        when "../source-ipv6-address";
                        description "The default value is 128 when source IPv6 address is configured.";
                      }
                    }
                    description
                      "Source IPv6 address mask.";
                  }
                  leaf destination-ipv6-address {
                    type inet:ipv6-address-no-zone;
                    description
                      "Destination IPv6 address.";
                  }
                  leaf destination-ipv6-mask {
                    type uint8 {
                      range "1..128";
                    }
                    ext:dynamic-default {
                      ext:default-value "128" {
                        when "../destination-ipv6-address";
                        description "The default value is 128 when destination IPv6 address is configured.";
                      }
                    }
                    description
                      "Destination IPv6 address mask.";
                  }
                }
              }
              leaf protocol {
                type uint8 {
                  range "0..254";
                  ext:value-meaning {
                    ext:item  "6" {
                      ext:meaning "tcp";
                    }
                    ext:item  "17" {
                      ext:meaning "udp";
                    }
                    ext:item  "132" {
                      ext:meaning "sctp";
                    }
                  }
                }
                description
                  "Protocol of an IFIT whitelist rule.";
              }
              leaf source-port {
                type uint16 {
                  range "1..65535";
                }
                must "../protocol=6 or ../protocol=17 or ../protocol=132";
                description
                  "Source port of an IFIT whitelist rule.";
              }
              leaf source-port-end {
                type uint16 {
                  range "1..65535";
                }
                description
                  "Source end port of an IFIT whitelist rule.";
              }
              leaf destination-port {
                type uint16 {
                  range "1..65535";
                }
                must "../protocol=6 or ../protocol=17 or ../protocol=132";
                description
                  "Destination port of an IFIT whitelist rule.";
              }
              leaf destination-port-end {
                type uint16 {
                  range "1..65535";
                }
                description
                  "Destination end port of an IFIT whitelist rule.";
              }
            }
          }
        }
      }
      container native-ip-learning {
        presence "Flow learning.";
        description
          "Configure IFIT flow learning for native IP.";
        leaf interval {
          type uint16 {
            range "10|60";
          }
          units "s";
          default "60";
          description
            "Interval of IFIT for native IP. The interval should be the same on the entire network. Otherwise, the statistics may be inaccurate.";
        }
        leaf color-flag {
          type native-ip-color-flag;
          default "flags-bit0";
          description
            "Color flag of IFIT for native IP. The color flag should be the same on the entire network. Otherwise, the statistics may be inaccurate.";
        }
        leaf report-loss-enable {
          type boolean;
          default "false";
          description
            "Enable/disable forwarding loss reason report of IFIT for native IP.";
        }
        container bind-learning-interfaces {
          description
            "List of interface for native IP flow learning.";
          list bind-learning-interface {
            key "interface-name rule-name";
            description
              "Configure flow learning specified interface of native IP.";
            leaf interface-name {
              type leafref {
                path "/ifm:ifm/ifm:interfaces/ifm:interface/ifm:name";
              }
              description
                "Interface name to which the native IP flow learning binds.";
            }
            leaf rule-name {
              type leafref {
                path "/ifit:ifit/ifit-common:ifit-common/ifit-common:whitelist-groups/ifit-common:whitelist-group/ifit-common:whitelist-rules/ifit-common:whitelist-rule/ifit-common:rule-name";
              }
              description
                "Whitelist rule name.";
            }
            leaf direction {
              type flow-direction;
              mandatory true;
              description
                "Specify the measurement direction of native IP.";
            }
            leaf flow-type {
              type flow-type;
              must "../flow-type='unidirection' or (../../../../whitelist-groups/whitelist-group/whitelist-rules/whitelist-rule[rule-name=current()/../rule-name]/source-ipv4-address and ../../../../whitelist-groups/whitelist-group/whitelist-rules/whitelist-rule[rule-name=current()/../rule-name]/destination-ipv4-address)";
              default "unidirection";
              description
                "Specify the flow type of the native IP flow learning.";
            }
          }
        }
      }
      container srv6-segment-list-flows {
        config false;
        description
          "List of SRv6 segment list flows of IFIT.";
        list srv6-segment-list-flow {
          key "flow-id segment-list-id";
          description
            "Operational data of SRv6 segment list flow of IFIT.";
          leaf flow-id {
            type uint64;
            description
              "Flow ID of an IFIT flow.";
          }
          leaf segment-list-id {
            type uint32;
            description
              "Segment list ID of an IFIT flow.";
          }
          leaf flow-type {
            type ifit-common:flow-type;
            description
              "Flow type of an IFIT flow.";
          }
          leaf loss-measure-enable {
            type boolean;
            description
              "Enable/disable loss measure function of an IFIT flow.";
          }
          leaf delay-measure-enable {
            type boolean;
            description
              "Enable/disable delay measure function of an IFIT flow.";
          }
          leaf measure-mode {
            type ifit-common:measure-mode;
            description
              "Measure mode of an IFIT flow.";
          }
          leaf interval {
            type uint16 {
              range "2|10|30|60|300";
            }
            units "s";
            description
              "Interval of an IFIT flow.";
          }
          leaf color {
            type uint32;
            description
              "Color of an IFIT flow.";
          }
          leaf binding-sid {
            type inet:ipv6-address-no-zone;
            description
              "Binding sid of an IFIT flow.";
          }
          leaf reverse-binding-sid {
            type inet:ipv6-address-no-zone;
            description
              "Reverse binding sid of an IFIT flow.";
          }
          leaf end-point {
            type inet:ipv6-address-no-zone;
            description
              "End point of an IFIT flow.";
          }
        }
      }
      container work-mode {
        presence "Work mode.";
        description
          "Configure IFIT work mode.";
        leaf mode {
          type ifit-common:work-mode;
          mandatory true;
          description
            "Mode of IFIT.";
        }
        leaf service-type {
          type ifit-common:service-type;
          description
            "Service type of IFIT.";
        }
      }
      container flow-statistic-results {
        config false;
        description
          "List of statistic results of flows.";
        list flow-statistic-result {
          key "flow-id segment-list-id";
          description
            "Statistics of SRv6 segment list flow of IFIT.";
          leaf flow-id {
            type uint64;
            description
              "Flow ID of an IFIT flow.";
          }
          leaf segment-list-id {
            type uint32;
            description
              "Segment list ID of an IFIT flow.";
          }
          leaf color {
            type uint32;
            description
              "Color of an IFIT flow.";
          }
          leaf end-point {
            type inet:ipv6-address-no-zone;
            description
              "End point of an IFIT flow.";
          }
          container one-way-delays {
            description
              "List of one-way delay data.";
            list one-way-delay {
              key "period";
              description
                "Statistics of data of one-way delay measurement.";
              leaf period {
                type uint64;
                description
                  "Data period of one-way delay measurement.";
              }
              leaf local-delay {
                type int64;
                units "ns";
                description
                  "Local delay result.";
              }
              leaf local-delay-jitter {
                type uint64;
                units "ns";
                description
                  "Local delay jitter result.";
              }
              leaf remote-delay {
                type int64;
                units "ns";
                description
                  "Remote delay result.";
              }
              leaf remote-delay-jitter {
                type uint64;
                units "ns";
                description
                  "Remote delay jitter result.";
              }
            }
          }
          container two-way-delays {
            description
              "List of two-way delay data.";
            list two-way-delay {
              key "period";
              description
                "Statistics of data of two-way delay measurement.";
              leaf period {
                type uint64;
                description
                  "Data period of two-way delay measurement.";
              }
              leaf delay {
                type uint64;
                units "ns";
                description
                  "Two-way delay result.";
              }
              leaf jitter {
                type uint64;
                units "ns";
                description
                  "Two-way jitter result.";
              }
            }
          }
          container one-way-losses {
            description
              "List of one-way loss data.";
            list one-way-loss {
              key "period";
              description
                "Statistics of data of one-way loss measurement.";
              leaf period {
                type uint64;
                description
                  "Data period of one-way loss measurement.";
              }
              leaf local-loss {
                type uint64;
                description
                  "Local loss result.";
              }
              leaf local-loss-ratio {
                type uint32;
                description
                  "Local loss result.";
              }
              leaf remote-loss {
                type uint64;
                description
                  "Remote loss result.";
              }
              leaf remote-loss-ratio {
                type uint32;
                description
                  "Remote loss result.";
              }
            }
          }
        }
      }
    }
  }
  augment "/ni:network-instance/ni:instances/ni:instance" {
    description
      "The IFIT configuration in vpn.";
    container ifit-learning {
      when "/ifit:ifit";
      must "/ifit:ifit/ifit-common:ifit-common/ifit-common:global/ifit-common:clock-mode='common'";
      presence "Flow learning.";
      description
        "Configure IFIT flow learning for the VPN.";
      leaf flow-type {
        type ifit-common:flow-type;
        default "bidirection";
        description
          "Flow type of the IFIT flow learning.";
      }
      leaf interval {
        type uint16 {
          range "10|30|60|300";
        }
        units "s";
        default "60";
        description
          "Interval of the IFIT flow learning.";
      }
      leaf measure-mode {
        type ifit-common:measure-mode;
        default "e2e";
        description
          "Measure mode of the IFIT flow learning.";
      }
      leaf learning-mode {
        type ifit-common:learning-mode;
        default "sip-mask-dip-exact";
        description
          "Learning mode of the IFIT flow learning.";
      }
      leaf per-packet-delay-measure {
        type boolean;
        default "false";
        description
          "Enable/disable per packet delay measure function for the IFIT flow learning.";
      }
      leaf mapping-color-flag {
        type operate-color-flag-type;
        description
          "Mapping and operating color flag when learning flow.";
      }
      container bind-learning-interface {
        when "/ifit:ifit/ifit-common:ifit-common/ifit-common:global/ifit-common:node-id";
        description
          "Configure interface for IFIT flow learning.";
        choice learning-interface {
          description
            "Specify interface parameter.";
          case all-interfaces {
            description
              "Specify all interfaces.";
            container all-interfaces {
              presence "Bind all interfaces.";
              description
                "Configure all interfaces for IFIT flow learning.";
              leaf all {
                type empty;
                mandatory true;
                description
                  "All interfaces.";
              }
              leaf group-name {
                type leafref {
                  path "/ifit:ifit/ifit-common:ifit-common/ifit-common:whitelist-groups/ifit-common:whitelist-group/ifit-common:group-name";
                }
                description
                  "Whitelist group name.";
              }
            }
          }
          case specified-interface {
            description
              "Specify interface name.";
            container specified-interfaces {
              description
                "List of flow learning specified interfaces of IFIT.";
              list specified-interface {
                key "interface-name";
                description
                  "Configure flow learning specified interface of IFIT.";
                leaf interface-name {
                  type leafref {
                    path "/ifm:ifm/ifm:interfaces/ifm:interface/ifm:name";
                  }
                  description
                    "Interface name to which an IFIT flow learning binds.";
                }
                leaf group-name {
                  type leafref {
                    path "/ifit:ifit/ifit-common:ifit-common/ifit-common:whitelist-groups/ifit-common:whitelist-group/ifit-common:group-name";
                  }
                  description
                    "Whitelist group name.";
                }
              }
            }
          }
        }
      }
    }
  }
  augment "/ifm:ifm/ifm:interfaces/ifm:interface" {  
    description
      "The IFIT configuration in interface.";
    container ifit {
      when "/ifit:ifit";
      description
        "Configure IFIT mapping on the interface.";
      container mappings {
        when "../../ifm:vrf-name != '_public_'";
        description
          "List of configure IFIT mapping on the local interface.";
        list mapping {
          key "mapping-type";
          description
            "Configure IFIT mapping on the local interface.";
          leaf mapping-type {
            type ifit-common:mapping-type;
            description
              "Mapping type of IFIT.";
          }
        }
      }	
      container mapping-color-flag-egress {
        description
          "Configure enable/disable mapping color flag on egress interface.";
        leaf mapping-color-flag-egress {
          type boolean;
            default "false";
            description
              "Enable/disable mapping color flag on egress interface.";
        }
      }
    }
  }
}
