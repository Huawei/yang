/*
Copyright (C) 2021 Huawei Technologies Co., Ltd. All rights reserved.
*/
module huawei-routing-deviations-NE5000E {
  namespace "urn:huawei:yang:huawei-routing-deviations-NE5000E";
  prefix rt-devs-NE5000E;

  import huawei-routing {
    prefix rt;
  }
  import huawei-l3vpn {
    prefix l3vpn;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-routing module.";

  revision 2021-05-07 {
    description
      "Initial revision.";
    reference "Huawei private.";
  }

  typedef ipv6-protocol-type-deviations {
    type enumeration {
      enum init {
        value 0;
        description
          "Initial.";
      }
      enum direct {
        value 1;
        description
          "Direct.";
      }
      enum isis {
        value 3;
        description
          "Intermediate System-to-Intermediate System.";
      }
      enum static {
        value 4;
        description
          "Static.";
      }
      enum bgp {
        value 6;
        description
          "Border Gateway Protocol.";
      }
      enum ospfv3 {
        value 7;
        description
          "OSPFv3.";
      }
      enum ripng {
        value 8;
        description
          "Routing Information Protocol next generation.";
      }
      enum total {
        value 9;
        description
          "All protocols.";
      }
    }
    description
      "Protocol type.";
  }

  typedef ipv6-statistic-protocol-type-deviations {
    type enumeration {
      enum direct {
        value 1;
        description
          "Direct.";
      }
      enum static {
        value 2;
        description
          "Static.";
      }
      enum ripng {
        value 4;
        description
          "Routing Information Protocol next generation.";
      }
      enum ospfv3 {
        value 6;
        description
          "OSPFv3.";
      }
      enum isis {
        value 7;
        description
          "Intermediate System-to-Intermediate System.";
      }
      enum bgp {
        value 8;
        description
          "Border Gateway Protocol.";
      }
      enum total {
        value 12;
        description
          "All protocols.";
      }
    }
    description
      "Route statistic protocol type.";
  }

  typedef protocol-type-deviations {
    type enumeration {
      enum init {
        value 0;
        description
          "Initial.";
      }
      enum direct {
        value 1;
        description
          "Direct.";
      }
      enum ospf {
        value 2;
        description
          "Open Shortest Path First.";
      }
      enum isis {
        value 3;
        description
          "Intermediate System-to-Intermediate System.";
      }
      enum static {
        value 4;
        description
          "Static.";
      }
      enum rip {
        value 5;
        description
          "Routing Information Protocol.";
      }
      enum bgp {
        value 6;
        description
          "Border Gateway Protocol.";
      }
      enum total {
        value 9;
        description
          "All protocols.";
      }
    }
    description
      "Protocol type.";
  }

  typedef statistic-protocol-type-deviations {
    type enumeration {
      enum direct {
        value 1;
        description
          "Direct.";
      }
      enum static {
        value 2;
        description
          "Static.";
      }
      enum rip {
        value 3;
        description
          "Routing Information Protocol.";
      }
      enum ospf {
        value 5;
        description
          "Open Shortest Path First.";
      }
      enum isis {
        value 7;
        description
          "Intermediate System-to-Intermediate System.";
      }
      enum bgp {
        value 8;
        description
          "Border Gateway Protocol.";
      }
      enum total {
        value 12;
        description
          "All protocols.";
      }
    }
    description
      "Route statistic protocol type.";
  }

  deviation "/rt:static-unicast-route-number" {
    deviate not-supported;
  }
  deviation "/rt:ipv4-unicast-route-number" {
    deviate not-supported;
  }
  deviation "/rt:ipv6-unicast-route-number" {
    deviate not-supported;
  }
  deviation "/ni:network-instance/ni:instances/ni:instance/l3vpn:afs/l3vpn:af/rt:routing/rt:routing-manage/rt:topologys/rt:topology/rt:routes/rt:ipv4-unicast-routes/rt:ipv4-unicast-route/rt:tunnel-id" {
    deviate not-supported;
  }
  deviation "/ni:network-instance/ni:instances/ni:instance/l3vpn:afs/l3vpn:af/rt:routing/rt:routing-manage/rt:topologys/rt:topology/rt:routes/rt:ipv4-unicast-routes/rt:ipv4-unicast-route/rt:nexthop-vrf-name" {
    deviate not-supported;
  }
  deviation "/ni:network-instance/ni:instances/ni:instance/l3vpn:afs/l3vpn:af/rt:routing/rt:routing-manage/rt:topologys/rt:topology/rt:routes/rt:ipv4-unicast-routes/rt:ipv4-unicast-route/rt:relay-nexthop" {
    deviate not-supported;
  }
  deviation "/ni:network-instance/ni:instances/ni:instance/l3vpn:afs/l3vpn:af/rt:routing/rt:routing-manage/rt:topologys/rt:topology/rt:routes/rt:ipv4-unicast-routes/rt:ipv4-unicast-route/rt:nexthop-interface-name" {
    deviate not-supported;
  }
  deviation "/ni:network-instance/ni:instances/ni:instance/l3vpn:afs/l3vpn:af/rt:routing/rt:routing-manage/rt:topologys/rt:topology/rt:routes/rt:ipv6-unicast-routes/rt:ipv6-unicast-route/rt:tunnel-type" {
    deviate not-supported;
  }
  deviation "/ni:network-instance/ni:instances/ni:instance/l3vpn:afs/l3vpn:af/rt:routing/rt:routing-manage/rt:topologys/rt:topology/rt:routes/rt:ipv6-unicast-routes/rt:ipv6-unicast-route/rt:tunnel-id" {
    deviate not-supported;
  }
  deviation "/ni:network-instance/ni:instances/ni:instance/l3vpn:afs/l3vpn:af/rt:routing/rt:routing-manage/rt:topologys/rt:topology/rt:routes/rt:ipv6-unicast-routes/rt:ipv6-unicast-route/rt:nexthop-vrf-name" {
    deviate not-supported;
  }
  deviation "/ni:network-instance/ni:instances/ni:instance/l3vpn:afs/l3vpn:af/rt:routing/rt:routing-manage/rt:topologys/rt:topology/rt:routes/rt:ipv6-unicast-routes/rt:ipv6-unicast-route/rt:relay-nexthop" {
    deviate not-supported;
  }
  deviation "/ni:network-instance/ni:instances/ni:instance/l3vpn:afs/l3vpn:af/rt:routing/rt:routing-manage/rt:topologys/rt:topology/rt:routes/rt:ipv6-unicast-routes/rt:ipv6-unicast-route/rt:tunnel-types" {
    deviate not-supported;
  }
  deviation "/ni:network-instance/ni:instances/ni:instance/l3vpn:afs/l3vpn:af/rt:routing/rt:direct-routing/rt:interfaces/rt:interface/rt:cost" {
    deviate not-supported;
  }
  deviation "/ni:network-instance/ni:instances/ni:instance/l3vpn:afs/l3vpn:af/rt:routing/rt:direct-routing/rt:interfaces/rt:interface/rt:degrade-cost" {
    deviate not-supported;
  }
  deviation "/ni:network-instance/ni:instances/ni:instance/l3vpn:afs/l3vpn:af/rt:routing/rt:static-routing/rt:unicast-routes/rt:unicast-route/rt:dhcp-enable" {
    deviate not-supported;
  }
  deviation "/ni:network-instance/ni:instances/ni:instance/l3vpn:afs/l3vpn:af/rt:routing/rt:static-routing/rt:unicast-routes/rt:unicast-route/rt:relay-arp-vlink-route" {
    deviate not-supported;
  }
  deviation "/ni:network-instance/ni:instances/ni:instance/l3vpn:afs/l3vpn:af/rt:routing/rt:static-routing/rt:unicast-routes/rt:unicast-route/rt:track-setting/rt:efm" {
    deviate not-supported;
  }
  deviation "/ni:network-instance/ni:instances/ni:instance/l3vpn:afs/l3vpn:af/rt:routing/rt:static-routing/rt:unicast-route2s/rt:unicast-route2/rt:nexthop-interfaces/rt:nexthop-interface/rt:dhcp-enable" {
    deviate not-supported;
  }
  deviation "/ni:network-instance/ni:instances/ni:instance/l3vpn:afs/l3vpn:af/rt:routing/rt:static-routing/rt:unicast-route2s/rt:unicast-route2/rt:nexthop-interfaces/rt:nexthop-interface/rt:track-setting/rt:efm" {
    deviate not-supported;
  }
  deviation "/ni:network-instance/ni:instances/ni:instance/l3vpn:afs/l3vpn:af/rt:routing/rt:static-routing/rt:unicast-route2s/rt:unicast-route2/rt:nexthop-interface-addresses/rt:nexthop-interface-address/rt:track-setting/rt:efm" {
    deviate not-supported;
  }
  deviation "/ni:network-instance/ni:instances/ni:instance/l3vpn:afs/l3vpn:af/rt:routing/rt:static-routing/rt:unicast-route2s/rt:unicast-route2/rt:nexthop-addresses/rt:nexthop-address/rt:relay-arp-vlink-route" {
    deviate not-supported;
  }
  deviation "/ni:network-instance/ni:instances/ni:instance/l3vpn:afs/l3vpn:af/rt:routing/rt:static-routing/rt:unicast-route2s/rt:unicast-route2/rt:nexthop-addresses/rt:nexthop-address/rt:track-setting/rt:efm" {
    deviate not-supported;
  }
  deviation "/ni:network-instance/ni:instances/ni:instance/l3vpn:afs/l3vpn:af/rt:routing/rt:static-routing/rt:unicast-route2s/rt:unicast-route2/rt:nexthop-sdwans" {
    deviate not-supported;
  }
  deviation "/ni:network-instance/ni:instances/ni:instance/l3vpn:afs/l3vpn:af/rt:routing/rt:static-routing/rt:unicast-route2s/rt:unicast-route2/rt:nexthop-vrf-addresses/rt:nexthop-vrf-address/rt:relay-arp-vlink-route" {
    deviate not-supported;
  }
  deviation "/ni:network-instance/ni:instances/ni:instance/l3vpn:afs/l3vpn:af/rt:routing/rt:static-routing/rt:unicast-route2s/rt:unicast-route2/rt:nexthop-vrf-addresses/rt:nexthop-vrf-address/rt:track-setting/rt:efm" {
    deviate not-supported;
  }
  deviation "/ni:network-instance/ni:instances/ni:instance/l3vpn:afs/l3vpn:af/rt:routing/rt:static-routing/rt:unicast-route2s/rt:unicast-route2/rt:nexthop-vrf-sdwans" {
    deviate not-supported;
  }
  deviation "/ni:network-instance/ni:instances/ni:instance/l3vpn:afs/l3vpn:af/rt:routing/rt:static-routing/rt:bfd-templates/rt:bfd-template/rt:dhcp-enable" {
    deviate not-supported;
  }
  deviation "/rt:routing/rt:routing-manage/rt:ipv4-vpn-route-statisticss/rt:ipv4-vpn-route-statistics/rt:protocol-type" {
    deviate replace {
      type rt-devs-NE5000E:statistic-protocol-type-deviations;
    }
  }
  deviation "/rt:routing/rt:routing-manage/rt:ipv6-vpn-route-statisticss/rt:ipv6-vpn-route-statistics/rt:protocol-type" {
    deviate replace {
      type rt-devs-NE5000E:ipv6-statistic-protocol-type-deviations;
    }
  }
  deviation "/rt:reset-route-statistics/rt:input/rt:protocol-type" {
    deviate replace {
      type rt-devs-NE5000E:statistic-protocol-type-deviations;
    }
  }
  deviation "/ni:network-instance/ni:instances/ni:instance/l3vpn:afs/l3vpn:af/rt:routing/rt:routing-manage/rt:topologys/rt:topology/rt:routes/rt:ipv4-unicast-routes/rt:ipv4-unicast-route/rt:protocol-type" {
    deviate replace {
      type rt-devs-NE5000E:protocol-type-deviations;
    }
  }
  deviation "/ni:network-instance/ni:instances/ni:instance/l3vpn:afs/l3vpn:af/rt:routing/rt:routing-manage/rt:topologys/rt:topology/rt:routes/rt:ipv6-unicast-routes/rt:ipv6-unicast-route/rt:protocol-type" {
    deviate replace {
      type rt-devs-NE5000E:ipv6-protocol-type-deviations;
    }
  }
  deviation "/ni:network-instance/ni:instances/ni:instance/l3vpn:afs/l3vpn:af/rt:routing/rt:routing-manage/rt:topologys/rt:topology/rt:routes/rt:ipv4-route-statistics/rt:ipv4-route-statistic/rt:protocol-type" {
    deviate replace {
      type rt-devs-NE5000E:statistic-protocol-type-deviations;
    }
  }
  deviation "/ni:network-instance/ni:instances/ni:instance/l3vpn:afs/l3vpn:af/rt:routing/rt:routing-manage/rt:topologys/rt:topology/rt:routes/rt:ipv6-route-statistics/rt:ipv6-route-statistic/rt:protocol-type" {
    deviate replace {
      type rt-devs-NE5000E:ipv6-statistic-protocol-type-deviations;
    }
  }
  deviation "/ni:network-instance/ni:instances/ni:instance/l3vpn:afs/l3vpn:af/rt:routing/rt:direct-routing/rt:interfaces/rt:interface" {
    deviate delete {
      must 'cost or degrade-cost or binding-topologys';
    }
    deviate add {
      must 'binding-topologys';
    }
  }
  deviation "/ni:network-instance/ni:instances/ni:instance/l3vpn:afs/l3vpn:af/rt:routing/rt:static-routing/rt:unicast-routes/rt:unicast-route/rt:cost" {
    deviate delete {
      must "../ldp-sync='false'";
    }
    deviate add {
      must "(../../../../../l3vpn:type != 'ipv4-unicast') and (../ldp-sync='false')";
    }
  }
  deviation "/ni:network-instance/ni:instances/ni:instance/l3vpn:afs/l3vpn:af/rt:routing/rt:static-routing/rt:unicast-routes/rt:unicast-route/rt:ldp-sync" {
    deviate add {
      must "(../permanent='false' and ../no-advertise='false' and ../no-install='false' and ../../../../../l3vpn:type='ipv4-unicast') or ../ldp-sync='false' ";
    }
  }
  deviation "/ni:network-instance/ni:instances/ni:instance/l3vpn:afs/l3vpn:af/rt:routing/rt:static-routing/rt:unicast-route2s/rt:unicast-route2/rt:topology-name" {
    deviate delete {
      must "(../../../../../../../ni:name='_public_' or ../topology-name='base') and (count(../nexthop-interfaces/nexthop-interface)> 0 or count(../nexthop-interface-addresses/nexthop-interface-address)> 0 or count(../nexthop-addresses/nexthop-address)> 0 or count(../nexthop-sdwans/nexthop-sdwan)> 0 or count(../nexthop-vrf-addresses/nexthop-vrf-address)> 0 or count(../nexthop-vrf-sdwans/nexthop-vrf-sdwan)> 0 or count(../nexthop-vrf-onlys/nexthop-vrf-only)> 0 or count(../v4-via-v6-interface-addresses/v4-via-v6-interface-address)> 0 or count(../v4-via-v6-addresses/v4-via-v6-address)> 0 or count(../v4-via-v6-vrf-addresses/v4-via-v6-vrf-address)> 0)";
    }
    deviate add {
      must "(../../../../../../../ni:name='_public_' or ../topology-name='base') and (count(../nexthop-interfaces/nexthop-interface)> 0 or count(../nexthop-interface-addresses/nexthop-interface-address)> 0 or count(../nexthop-addresses/nexthop-address)> 0 or count(../nexthop-vrf-addresses/nexthop-vrf-address)> 0 or count(../nexthop-vrf-onlys/nexthop-vrf-only)> 0 or count(../v4-via-v6-interface-addresses/v4-via-v6-interface-address)> 0 or count(../v4-via-v6-addresses/v4-via-v6-address)> 0 or count(../v4-via-v6-vrf-addresses/v4-via-v6-vrf-address)> 0)";
    }
  }
  deviation "/ni:network-instance/ni:instances/ni:instance/l3vpn:afs/l3vpn:af/rt:routing/rt:static-routing/rt:unicast-route2s/rt:unicast-route2/rt:nexthop-interfaces/rt:nexthop-interface/rt:cost" {
    deviate delete {
      must "../ldp-sync='false'";
    }
    deviate add {
      must "(../../../../../../../l3vpn:type != 'ipv4-unicast') and (../ldp-sync='false')";
    }
  }
  deviation "/ni:network-instance/ni:instances/ni:instance/l3vpn:afs/l3vpn:af/rt:routing/rt:static-routing/rt:unicast-route2s/rt:unicast-route2/rt:nexthop-interfaces/rt:nexthop-interface/rt:ldp-sync" {
    deviate add {
      must "(../permanent='false' and ../no-advertise='false' and ../no-install='false' and ../../../../../../../l3vpn:type='ipv4-unicast') or ../ldp-sync='false' ";
    }
  }
  deviation "/ni:network-instance/ni:instances/ni:instance/l3vpn:afs/l3vpn:af/rt:routing/rt:static-routing/rt:unicast-route2s/rt:unicast-route2/rt:nexthop-interfaces/rt:nexthop-interface/rt:track-setting/rt:bfd-enable/rt:bfd-enable" {
    deviate delete {
      must "(../permanent='false' and ../../../topology-name='base' and ../dhcp-enable='true') and ../bfd-enable='true'";
    }
    deviate add {
      must "(../permanent='false' and ../../../topology-name='base') and ../bfd-enable='true'";
    }
  }
  deviation "/ni:network-instance/ni:instances/ni:instance/l3vpn:afs/l3vpn:af/rt:routing/rt:static-routing/rt:unicast-route2s/rt:unicast-route2/rt:nexthop-interface-addresses/rt:nexthop-interface-address/rt:cost" {
    deviate delete {
      must "../ldp-sync='false'";
    }
    deviate add {
      must "(../../../../../../../l3vpn:type != 'ipv4-unicast') and (../ldp-sync='false')";
    }
  }
  deviation "/ni:network-instance/ni:instances/ni:instance/l3vpn:afs/l3vpn:af/rt:routing/rt:static-routing/rt:unicast-route2s/rt:unicast-route2/rt:nexthop-interface-addresses/rt:nexthop-interface-address/rt:ldp-sync" {
    deviate add {
      must "(../permanent='false' and ../no-advertise='false' and ../no-install='false' and ../../../../../../../l3vpn:type='ipv4-unicast') or ../ldp-sync='false' ";
    }
  }
}
