/*
Copyright (C) 2021 Huawei Technologies Co., Ltd. All rights reserved.
*/
module huawei-openconfig-alarms-deviations-NE5000E {
  namespace "urn:huawei:yang:huawei-openconfig-alarms-deviations-NE5000E";
  prefix oc-alarms-devs-NE5000E;

  import openconfig-alarms {
    prefix oc-alarms;
  }
  import openconfig-platform {
    prefix oc-platform;
  }

  organization
    "Huawei Technologies Co., Ltd.";
  contact
    "Huawei Industrial Base
     Bantian, Longgang
     Shenzhen 518129
     People's Republic of China
     Website: http://www.huawei.com
     Email: support@huawei.com";
  description
    "This module defines deviation statements for openconfig-alarms module.";

  revision 2021-05-07 {
    description
      "Initial revision.";
    reference "Huawei private.";
  }

  deviation "/oc-platform:components/oc-platform:component/oc-platform:state/oc-alarms:equipment-failure" {
    deviate not-supported;
  }
  deviation "/oc-platform:components/oc-platform:component/oc-platform:state/oc-alarms:equipment-mismatch" {
    deviate not-supported;
  }
}
