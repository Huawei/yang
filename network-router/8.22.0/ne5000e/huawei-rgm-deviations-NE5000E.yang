/*
Copyright (C) 2021 Huawei Technologies Co., Ltd. All rights reserved.
*/
module huawei-rgm-deviations-NE5000E {
  namespace "urn:huawei:yang:huawei-rgm-deviations-NE5000E";
  prefix rgm-devs-NE5000E;

  import huawei-rgm {
    prefix rgm;
  }
  import huawei-ifm {
    prefix ifm;
  }
  import huawei-ip {
    prefix ip;
  }

  organization
    "Huawei Technologies Co., Ltd.";
  contact
    "Huawei Industrial Base
     Bantian, Longgang
     Shenzhen 518129
     People's Republic of China
     Website: http://www.huawei.com
     Email: support@huawei.com";
  description
    "This module defines deviation statements for huawei-rgm module.";

  revision 2021-05-07 {
    description
      "Initial revision.";
    reference "Huawei private.";
  }

  deviation "/ifm:ifm/ifm:interfaces/ifm:interface/ip:ipv4/rgm:rgm/rgm:rgm-track/rgm:track-pw" {
    deviate not-supported;
  }
  deviation "/ifm:ifm/ifm:interfaces/ifm:interface/ip:ipv4/rgm:rgm/rgm:track-trunk" {
    deviate not-supported;
  }
  deviation "/ifm:ifm/ifm:interfaces/ifm:interface/ip:ipv4/rgm:rgm/rgm:track-rtmtg" {
    deviate not-supported;
  }
  deviation "/ifm:ifm/ifm:interfaces/ifm:interface/ip:ipv6/rgm:rgm6/rgm:rgm6-track/rgm:track-pw" {
    deviate not-supported;
  }
  deviation "/ifm:ifm/ifm:interfaces/ifm:interface/ip:ipv6/rgm:rgm6/rgm:rgm6-track/rgm:advertise-delay" {
    deviate not-supported;
  }
}
