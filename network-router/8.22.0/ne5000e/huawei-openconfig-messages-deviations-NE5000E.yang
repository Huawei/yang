/*
Copyright (C) 2021 Huawei Technologies Co., Ltd. All rights reserved.
*/
module huawei-openconfig-messages-deviations-NE5000E {
  namespace "urn:huawei:yang:huawei-openconfig-messages-deviations-NE5000E";
  prefix oc-messages-devs-NE5000E;

  import openconfig-messages {
    prefix oc-messages;
  }

  organization
    "Huawei Technologies Co., Ltd.";
  contact
    "Huawei Industrial Base
     Bantian, Longgang
     Shenzhen 518129
     People's Republic of China
     Website: http://www.huawei.com
     Email: support@huawei.com";
  description
    "This module defines deviation statements for openconfig-messages module.";

  revision 2021-05-07 {
    description
      "Initial revision.";
    reference "Huawei private.";
  }

  deviation "/oc-messages:messages" {
    deviate not-supported;
  }
}
