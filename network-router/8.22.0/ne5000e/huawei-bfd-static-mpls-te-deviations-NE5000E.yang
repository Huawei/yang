/*
Copyright (C) 2021 Huawei Technologies Co., Ltd. All rights reserved.
*/
module huawei-bfd-static-mpls-te-deviations-NE5000E {
  namespace "urn:huawei:yang:huawei-bfd-static-mpls-te-deviations-NE5000E";
  prefix bfd-static-mpls-te-devs-NE5000E;

  import huawei-bfd-static-mpls-te {
    prefix bfd-static-mpls-te;
  }
  import huawei-bfd {
    prefix bfd;
  }
  import huawei-devm {
    prefix devm;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd-static-mpls-te module.";

  revision 2021-05-07 {
    description
      "Initial revision.";
    reference "Huawei private.";
  }

  deviation "/bfd:bfd/bfd:sessions/bfd:session/bfd:session-type/bfd:static/bfd:static-session-link-type/bfd-static-mpls-te:te-lsp/bfd-static-mpls-te:sr-bit-err-det-static-te-lsp" {
    deviate not-supported;
  }
  deviation "/bfd:bfd/bfd:sessions/bfd:session/bfd:session-type/bfd:static/bfd:static-session-link-type/bfd-static-mpls-te:te-tunnel/bfd-static-mpls-te:select-board-slot-static-te-tunnel" {
    deviate not-supported;
  }
  deviation "/bfd:bfd/bfd:sessions/bfd:session/bfd:session-type/bfd:static/bfd:static-session-link-type/bfd-static-mpls-te:te-lsp/bfd-static-mpls-te:min-tx-interval-static-te-lsp" {
    deviate replace {
      type uint32 {
        range "10..1000";
      }
    }
  }
  deviation "/bfd:bfd/bfd:sessions/bfd:session/bfd:session-type/bfd:static/bfd:static-session-link-type/bfd-static-mpls-te:te-lsp/bfd-static-mpls-te:min-rx-interval-static-te-lsp" {
    deviate replace {
      type uint32 {
        range "10..1000";
      }
    }
  }
  deviation "/bfd:bfd/bfd:sessions/bfd:session/bfd:session-type/bfd:static/bfd:static-session-link-type/bfd-static-mpls-te:te-tunnel/bfd-static-mpls-te:min-tx-interval-static-te-tunnel" {
    deviate replace {
      type uint32 {
        range "10..1000";
      }
    }
  }
  deviation "/bfd:bfd/bfd:sessions/bfd:session/bfd:session-type/bfd:static/bfd:static-session-link-type/bfd-static-mpls-te:te-tunnel/bfd-static-mpls-te:min-rx-interval-static-te-tunnel" {
    deviate replace {
      type uint32 {
        range "10..1000";
      }
    }
  }
  deviation "/bfd:bfd/bfd:sessions/bfd:session/bfd:session-type/bfd:auto/bfd:auto-session-link-type/bfd-static-mpls-te:te-lsp/bfd-static-mpls-te:min-tx-interval-auto-te-lsp" {
    deviate replace {
      type uint32 {
        range "10..1000";
      }
    }
  }
  deviation "/bfd:bfd/bfd:sessions/bfd:session/bfd:session-type/bfd:auto/bfd:auto-session-link-type/bfd-static-mpls-te:te-lsp/bfd-static-mpls-te:min-rx-interval-auto-te-lsp" {
    deviate replace {
      type uint32 {
        range "10..1000";
      }
    }
  }
  deviation "/bfd:bfd/bfd:sessions/bfd:session/bfd:session-type/bfd:auto/bfd:auto-session-link-type/bfd-static-mpls-te:te-tunnel/bfd-static-mpls-te:min-tx-interval-auto-te-tunnel" {
    deviate replace {
      type uint32 {
        range "10..1000";
      }
    }
  }
  deviation "/bfd:bfd/bfd:sessions/bfd:session/bfd:session-type/bfd:auto/bfd:auto-session-link-type/bfd-static-mpls-te:te-tunnel/bfd-static-mpls-te:min-rx-interval-auto-te-tunnel" {
    deviate replace {
      type uint32 {
        range "10..1000";
      }
    }
  }
  deviation "/bfd:bfd/bfd:sessions/bfd:session/bfd-static-mpls-te:mpls-te-groups/bfd-static-mpls-te:mpls-te-group/bfd-static-mpls-te:sub-select-slot-id" {
    deviate replace {
      type leafref {
        path "/devm:devm/devm:lpu-boards/devm:lpu-board/devm:position";
      }
    }
  }
}
