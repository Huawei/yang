/*
Copyright (C) 2019 Huawei Technologies Co., Ltd. All rights reserved.
*/
submodule huawei-dhcp-client {
  belongs-to huawei-dhcp {
    prefix dhcp;
  }

  organization
    "Huawei Technologies Co., Ltd.";
  contact
    "Huawei Industrial Base
     Bantian, Longgang
     Shenzhen 518129
     People's Republic of China
     Website: http://www.huawei.com
     Email: support@huawei.com";
  description
    "This module contains a collection of YANG definitions for managing DHCP client.";

  revision 2019-12-22 {
    description
      "Initial revision.";
    reference
      "Huawei private.";
  }
  
  typedef client-state {
    type enumeration {
      enum "init" {
        value 0;
        description
          "Init state.";
      }
      enum "selecting" {
        value 1;
        description
          "Selecting state.";
      }
      enum "requesting" {
        value 2;
        description
          "Requesting state.";
      }
      enum "bound" {
        value 3;
        description
          "Bound state.";
      }
      enum "renewing" {
        value 4;
        description
          "Renewing state.";
      }
      enum "rebinding" {
        value 5;
        description
          "Rebinding state.";
      }
    }
    description
      "The type of client-state.";
  }
  grouping dhcp-client-type {
    description
      "Configure DHCP client attributes.";
    container global {
      description
        "Configure DHCP client global attributes.";
      leaf option60 {
        type string {
          length "1..128";
          pattern '([^\t]{1,})';
        }
        description
          "The value of DHCP client global option60.";
      }
      leaf unicast-flag {
        type empty;
        description
          "DHCP client unicast flag.";
      }
    }
  }
}
