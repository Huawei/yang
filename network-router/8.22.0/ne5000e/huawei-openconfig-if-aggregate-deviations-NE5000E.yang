/*
Copyright (C) 2021 Huawei Technologies Co., Ltd. All rights reserved.
*/
module huawei-openconfig-if-aggregate-deviations-NE5000E {
  namespace "urn:huawei:yang:huawei-openconfig-if-aggregate-deviations-NE5000E";
  prefix oc-lag-devs-NE5000E;

  import openconfig-if-aggregate {
    prefix oc-lag;
  }
  import openconfig-if-ethernet {
    prefix oc-eth;
  }
  import iana-if-type {
    prefix ianaift;
  }
  import openconfig-interfaces {
    prefix oc-if;
  }

  organization
    "Huawei Technologies Co., Ltd.";
  contact
    "Huawei Industrial Base
     Bantian, Longgang
     Shenzhen 518129
     People's Republic of China
     Website: http://www.huawei.com
     Email: support@huawei.com";
  description
    "This module defines deviation statements for openconfig-if-aggregate module.";

  revision 2021-05-07 {
    description
      "Initial revision.";
    reference "Huawei private.";
  }

  deviation "/oc-if:interfaces/oc-if:interface/oc-lag:aggregation/oc-lag:state/oc-lag:lag-speed" {
    deviate not-supported;
  }
  deviation "/oc-if:interfaces/oc-if:interface/oc-lag:aggregation/oc-lag:state/oc-lag:member" {
    deviate not-supported;
  }
  deviation "/oc-if:interfaces/oc-if:interface/oc-lag:aggregation/oc-lag:config/oc-lag:lag-type" {
    deviate add {
      default "STATIC";
    }
  }
  deviation "/oc-if:interfaces/oc-if:interface/oc-lag:aggregation/oc-lag:config/oc-lag:min-links" {
    deviate replace {
      type uint16 {
        range "1..64";
      }
    }
    deviate add {
      default "1";
    }
  }
  deviation "/oc-if:interfaces/oc-if:interface/oc-eth:ethernet/oc-eth:config/oc-lag:aggregate-id" {
    deviate add {
      must "../../../oc-if:config/oc-if:type = 'ianaift:ethernetCsmacd' and /oc-if:interfaces/oc-if:interface[oc-if:name = current()]/oc-if:config/oc-if:type = 'ianaift:ieee8023adLag'";
    }
  }
}
