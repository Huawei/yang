/*
Copyright (C) 2021 Huawei Technologies Co., Ltd. All rights reserved.
*/
module huawei-twamp-responder-deviations-NE5000E {
  namespace "urn:huawei:yang:huawei-twamp-responder-deviations-NE5000E";
  prefix twamp-responder-devs-NE5000E;

  import huawei-twamp-responder {
    prefix twamp-responder;
  }

  organization
    "Huawei Technologies Co., Ltd.";
  contact
    "Huawei Industrial Base
     Bantian, Longgang
     Shenzhen 518129
     People's Republic of China
     Website: http://www.huawei.com
     Email: support@huawei.com";
  description
    "This module defines deviation statements for huawei-twamp-responder module.";

  revision 2021-05-07 {
    description
      "Initial revision.";
    reference "Huawei private.";
  }

  deviation "/twamp-responder:twamp-responder/twamp-responder:responder/twamp-responder:test-sessions/twamp-responder:test-session/twamp-responder:if-name" {
    deviate not-supported;
  }
  deviation "/twamp-responder:twamp-responder/twamp-responder:responder/twamp-responder:test-sessions/twamp-responder:test-session" {
    deviate delete {
      must 'not(vrf-name) or not(if-name)';
    }
  }
  deviation "/twamp-responder:twamp-responder/twamp-responder:responder/twamp-responder:test-sessions/twamp-responder:test-session/twamp-responder:link-bundle-if" {
    deviate delete {
      must 'not(../if-name)';
    }
  }
}
