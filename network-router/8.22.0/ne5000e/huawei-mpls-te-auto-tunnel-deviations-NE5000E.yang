/*
Copyright (C) 2021 Huawei Technologies Co., Ltd. All rights reserved.
*/
module huawei-mpls-te-auto-tunnel-deviations-NE5000E {
  namespace "urn:huawei:yang:huawei-mpls-te-auto-tunnel-deviations-NE5000E";
  prefix mpls-te-auto-tunnel-devs-NE5000E;

  import huawei-mpls-te-auto-tunnel {
    prefix mpls-te-auto-tunnel;
  }
  import huawei-mpls-te {
    prefix mpls-te;
  }
  import huawei-mpls {
    prefix mpls;
  }

  organization
    "Huawei Technologies Co., Ltd.";
  contact
    "Huawei Industrial Base
     Bantian, Longgang
     Shenzhen 518129
     People's Republic of China
     Website: http://www.huawei.com
     Email: support@huawei.com";
  description
    "This module defines deviation statements for huawei-mpls-te-auto-tunnel module.";

  revision 2021-05-07 {
    description
      "Initial revision.";
    reference "Huawei private.";
  }

  deviation "/mpls:mpls/mpls-te:te/mpls-te-auto-tunnel:rsvp-te-auto-tunnels/mpls-te-auto-tunnel:rsvp-te-auto-tunnel/mpls-te-auto-tunnel:entropy-label-enable" {
    deviate not-supported;
  }
  deviation "/mpls:mpls/mpls-te:te/mpls-te-auto-tunnel:sr-te-auto-tunnels" {
    deviate not-supported;
  }
}
