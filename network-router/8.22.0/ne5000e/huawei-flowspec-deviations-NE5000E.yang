/*
Copyright (C) 2021 Huawei Technologies Co., Ltd. All rights reserved.
*/
module huawei-flowspec-deviations-NE5000E {
  namespace "urn:huawei:yang:huawei-flowspec-deviations-NE5000E";
  prefix flowspec-devs-NE5000E;

  import huawei-flowspec {
    prefix flowspec;
  }

  organization
    "Huawei Technologies Co., Ltd.";
  contact
    "Huawei Industrial Base
     Bantian, Longgang
     Shenzhen 518129
     People's Republic of China
     Website: http://www.huawei.com
     Email: support@huawei.com";
  description
    "This module defines deviation statements for huawei-flowspec module.";

  revision 2021-05-07 {
    description
      "Initial revision.";
    reference "Huawei private.";
  }

  deviation "/flowspec:flowspec/flowspec:ipv6-family/flowspec:interface-group-statisticss" {
    deviate not-supported;
  }
}
