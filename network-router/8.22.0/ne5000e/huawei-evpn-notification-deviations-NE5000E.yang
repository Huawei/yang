/*
Copyright (C) 2021 Huawei Technologies Co., Ltd. All rights reserved.
*/
module huawei-evpn-notification-deviations-NE5000E {
  namespace "urn:huawei:yang:huawei-evpn-notification-deviations-NE5000E";
  prefix evpn-notification-devs-NE5000E;

  import huawei-evpn-notification {
    prefix evpn-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-evpn-notification module.";

  revision 2021-05-07 {
    description
      "Initial revision.";
    reference "Huawei private.";
  }

  deviation "/evpn-notification:evpn-ringid-conflict-alm" {
    deviate not-supported;
  }
  deviation "/evpn-notification:evpn-ringid-conflict-alm-clear" {
    deviate not-supported;
  }
  deviation "/evpn-notification:evpn-qualify-bum-res-alm" {
    deviate not-supported;
  }
  deviation "/evpn-notification:evpn-qualify-bum-res-alm-clear" {
    deviate not-supported;
  }
}
