/*
Copyright (C) 2021 Huawei Technologies Co., Ltd. All rights reserved.
*/
module huawei-evpl-deviations-NE5000E {
  namespace "urn:huawei:yang:huawei-evpl-deviations-NE5000E";
  prefix evpl-devs-NE5000E;

  import huawei-evpl {
    prefix evpl;
  }

  organization
    "Huawei Technologies Co., Ltd.";
  contact
    "Huawei Industrial Base
     Bantian, Longgang
     Shenzhen 518129
     People's Republic of China
     Website: http://www.huawei.com
     Email: support@huawei.com";
  description
    "This module defines deviation statements for huawei-evpl module.";

  revision 2021-05-07 {
    description
      "Initial revision.";
    reference "Huawei private.";
  }

  typedef evpl-mode-deviations {
    type enumeration {
      enum mpls-mode {
        value 1;
        description
          "MPLS mode.";
      }
      enum srv6-mode {
        value 2;
        description
          "SRv6 mode.";
      }
      enum none {
        value 3;
        description
          "None mode.";
      }
    }
    description
      "The mode of EVPL instance.";
  }

  deviation "/evpl:evpl/evpl:instances/evpl:instance/evpl:peers" {
    deviate not-supported;
  }
  deviation "/evpl:evpl/evpl:instances/evpl:instance/evpl:evpl-statistics" {
    deviate not-supported;
  }
  deviation "/evpl:evpl/evpl:instances/evpl:instance/evpl:mode" {
    deviate replace {
      type evpl-devs-NE5000E:evpl-mode-deviations;
    }
  }
}
