/*
Copyright (C) 2021 Huawei Technologies Co., Ltd. All rights reserved.
*/
module huawei-clocksync-comm-deviations-NE5000E {
  namespace "urn:huawei:yang:huawei-clocksync-comm-deviations-NE5000E";
  prefix clocksync-comm-devs-NE5000E;

  import huawei-clocksync-comm {
    prefix clocksync-comm;
  }

  import huawei-ifm {
    prefix ifm;
  }

  organization
    "Huawei Technologies Co., Ltd.";

  contact
    "Huawei Industrial Base
     Bantian, Longgang
     Shenzhen 518129
     People's Republic of China
     Website: http://www.huawei.com
     Email: support@huawei.com";

  description
    "This module defines deviation statements for huawei-clocksync-comm module.";

  revision 2021-05-07 {
    description
      "Initial revision.";
    reference
      "Huawei private.";
  }

  deviation "/ifm:ifm/ifm:interfaces/ifm:interface/clocksync-comm:clocksync-flexe" {
    deviate not-supported;
  }

}
