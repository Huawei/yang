/*
Copyright (C) 2021 Huawei Technologies Co., Ltd. All rights reserved.
*/
module huawei-igmp-mld-deviations-NE5000E {
  namespace "urn:huawei:yang:huawei-igmp-mld-deviations-NE5000E";
  prefix igmp-mld-devs-NE5000E;

  import huawei-igmp-mld {
    prefix igmp-mld;
  }
  import huawei-ifm {
    prefix ifm;
  }
  import huawei-ethernet {
    prefix ethernet;
  }
  import huawei-multicast {
    prefix mc;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-igmp-mld module.";

  revision 2021-05-07 {
    description
      "Initial revision.";
    reference "Huawei private.";
  }

  deviation "/mc:multicast/igmp-mld:igmp/igmp-mld:disable-dhcp-stb-packet-copys" {
    deviate not-supported;
  }
  deviation "/ni:network-instance/ni:instances/ni:instance/igmp-mld:igmp/igmp-mld:interfaces/igmp-mld:interface/igmp-mld:entry-limit" {
    deviate not-supported;
  }
  deviation "/ni:network-instance/ni:instances/ni:instance/igmp-mld:igmp/igmp-mld:interfaces/igmp-mld:interface/igmp-mld:entry-limit-acl-name" {
    deviate not-supported;
  }
  deviation "/ni:network-instance/ni:instances/ni:instance/igmp-mld:igmp/igmp-mld:dot1q-static-groups" {
    deviate not-supported;
  }
  deviation "/ni:network-instance/ni:instances/ni:instance/igmp-mld:igmp/igmp-mld:qinq-static-groups" {
    deviate not-supported;
  }
  deviation "/ni:network-instance/ni:instances/ni:instance/igmp-mld:igmp/igmp-mld:qinq-groups" {
    deviate not-supported;
  }
  deviation "/ni:network-instance/ni:instances/ni:instance/igmp-mld:igmp/igmp-mld:qinq-ports" {
    deviate not-supported;
  }
  deviation "/ni:network-instance/ni:instances/ni:instance/igmp-mld:mld/igmp-mld:interfaces/igmp-mld:interface/igmp-mld:entry-limit" {
    deviate not-supported;
  }
  deviation "/ni:network-instance/ni:instances/ni:instance/igmp-mld:mld/igmp-mld:interfaces/igmp-mld:interface/igmp-mld:entry-limit-acl-name" {
    deviate not-supported;
  }
  deviation "/ni:network-instance/ni:instances/ni:instance/igmp-mld:mld/igmp-mld:dot1q-static-groups" {
    deviate not-supported;
  }
  deviation "/ni:network-instance/ni:instances/ni:instance/igmp-mld:mld/igmp-mld:qinq-static-groups" {
    deviate not-supported;
  }
  deviation "/ni:network-instance/ni:instances/ni:instance/igmp-mld:mld/igmp-mld:qinq-groups" {
    deviate not-supported;
  }
  deviation "/ni:network-instance/ni:instances/ni:instance/igmp-mld:mld/igmp-mld:qinq-ports" {
    deviate not-supported;
  }
  deviation "/ni:network-instance/ni:instances/ni:instance/igmp-mld:igmp/igmp-mld:global/igmp-mld:query-response-interval" {
    deviate replace {
      type uint32 {
        range "1..25";
      }
    }
  }
  deviation "/ni:network-instance/ni:instances/ni:instance/igmp-mld:igmp/igmp-mld:global/igmp-mld:last-member-query-interval" {
    deviate replace {
      type uint32 {
        range "1..5";
      }
    }
  }
  deviation "/ni:network-instance/ni:instances/ni:instance/igmp-mld:igmp/igmp-mld:interfaces/igmp-mld:interface/igmp-mld:query-response-interval" {
    deviate replace {
      type uint32 {
        range "1..25";
      }
    }
  }
  deviation "/ni:network-instance/ni:instances/ni:instance/igmp-mld:igmp/igmp-mld:interfaces/igmp-mld:interface/igmp-mld:last-member-query-interval" {
    deviate replace {
      type uint32 {
        range "1..5";
      }
    }
  }
  deviation "/ni:network-instance/ni:instances/ni:instance/igmp-mld:igmp/igmp-mld:static-groups/igmp-mld:static-group/igmp-mld:interface" {
    deviate delete {
      must 'not(/ifm:ifm/ifm:interfaces/ifm:interface[ifm:name=current()]/ethernet:ethernet/ethernet:main-interface/ethernet:l2-attribute)';
    }
  }
  deviation "/ni:network-instance/ni:instances/ni:instance/igmp-mld:mld/igmp-mld:global/igmp-mld:query-response-interval" {
    deviate replace {
      type uint32 {
        range "1..25";
      }
    }
  }
  deviation "/ni:network-instance/ni:instances/ni:instance/igmp-mld:mld/igmp-mld:global/igmp-mld:last-member-query-interval" {
    deviate replace {
      type uint32 {
        range "1..5";
      }
    }
  }
  deviation "/ni:network-instance/ni:instances/ni:instance/igmp-mld:mld/igmp-mld:interfaces/igmp-mld:interface/igmp-mld:query-response-interval" {
    deviate replace {
      type uint32 {
        range "1..25";
      }
    }
  }
  deviation "/ni:network-instance/ni:instances/ni:instance/igmp-mld:mld/igmp-mld:interfaces/igmp-mld:interface/igmp-mld:last-member-query-interval" {
    deviate replace {
      type uint32 {
        range "1..5";
      }
    }
  }
  deviation "/ni:network-instance/ni:instances/ni:instance/igmp-mld:mld/igmp-mld:static-groups/igmp-mld:static-group/igmp-mld:interface" {
    deviate delete {
      must 'not(/ifm:ifm/ifm:interfaces/ifm:interface[ifm:name=current()]/ethernet:ethernet/ethernet:main-interface/ethernet:l2-attribute)';
    }
  }
}
