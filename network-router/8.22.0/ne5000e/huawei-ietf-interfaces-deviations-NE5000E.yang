/*
Copyright (C) 2021 Huawei Technologies Co., Ltd. All rights reserved.
*/
module huawei-ietf-interfaces-deviations-NE5000E {
  namespace "urn:huawei:yang:huawei-ietf-interfaces-deviations-NE5000E";
  prefix if-devs-NE5000E;

  import ietf-interfaces {
    prefix if;
  }

  organization
    "Huawei Technologies Co., Ltd.";
  contact
    "Huawei Industrial Base
     Bantian, Longgang
     Shenzhen 518129
     People's Republic of China
     Website: http://www.huawei.com
     Email: support@huawei.com";
  description
    "This module defines deviation statements for ietf-interfaces module.";

  revision 2021-05-07 {
    description
      "Initial revision.";
    reference "Huawei private.";
  }

  deviation "/if:interfaces-state/if:interface/if:higher-layer-if" {
    deviate not-supported;
  }
  deviation "/if:interfaces-state/if:interface/if:lower-layer-if" {
    deviate not-supported;
  }
  deviation "/if:interfaces/if:interface/if:name" {
    deviate replace {
      type string {
        length "1..63";
      }
    }
  }
  deviation "/if:interfaces/if:interface/if:description" {
    deviate replace {
      type string {
        length "1..242";
      }
    }
  }
  deviation "/if:interfaces/if:interface/if:link-up-down-trap-enable" {
    deviate add {
      default "enabled";
    }
  }
  deviation "/if:interfaces-state/if:interface/if:name" {
    deviate replace {
      type string {
        length "1..63";
      }
    }
  }
}
