/*
Copyright (C) 2019-2022 Huawei Technologies Co., Ltd. All rights reserved.
*/
module huawei-module-management {
  namespace "urn:huawei:yang:huawei-module-management";
  prefix module-management;
  import ietf-yang-types {
    prefix yang;
  }
  import huawei-pub-type {
    prefix pub-type;
  }
  import ietf-inet-types {
    prefix inet;
  }
  import huawei-extension {
    prefix ext;
  }
  import huawei-file-operation {
    prefix file-operation;
  }
  
  organization
    "Huawei Technologies Co., Ltd.";
  contact
    "Huawei Industrial Base
     Bantian, Longgang
     Shenzhen 518129
     People's Republic of China
     Website: http://www.huawei.com
     Email: support@huawei.com";
  description
    "Module package management.";
  revision 2022-02-08 {
    description
      "Add enum fail to type status-type.";
    reference
      "Huawei private.";
  }
  revision 2022-01-21 {
    description
      "Add type transfer-protocol-type, plug-package-action-type, status-type. Add container loaded-plug-package-infos, activated-plug-package-version-infos, next-plug-package-version-infos, plug-package-action-results. Add rpc download-and-load-plug-package, activate-plug-package, delete-plug-package, startup-plug-package, reset-startup-plug-package.";
    reference
      "Huawei private.";
  }
  revision 2021-03-24 {
    description
      "Modify fail-reason node and modify check-module node properties.";
    reference
      "Huawei private.";
  }
  revision 2021-03-15 {
    description
      "Add fail-reason node and modify operation-schedules.";
    reference
      "Huawei private.";
  }
  revision 2021-02-24 {
    description
      "Add module-packages and modify next-startup-modules.";
    reference
      "Huawei private.";
  }  
  revision 2021-01-20 {
    description
      "Add check-type node and the enum of check-type. Add check-module node.";
    reference
      "Huawei private.";
  }  
  revision 2020-06-24 {
    description
      "Modify node description.";
    reference
      "Huawei private.";
  }  
  revision 2020-01-16 {
    description
      "Modify node properties.";
    reference
      "Huawei private.";
  }
  revision 2019-12-03 {
    description
      "Initial revision.";
    reference
      "Huawei private.";
  }

  ext:task-name "patch";
  typedef match-status { 
    type enumeration {
      enum "version-match" {
        value 0;
        description
          "The next startup MOD package matches the version of next startup base package.";
      }
      enum "version-not-match" {
        value 1;
        description
          "The next startup MOD package doesn't match the version of next startup base package.";
      }
    }
    description
      "Whether the next startup MOD package matches the version of the next startup base package.";
  }
  typedef module-state {
    type enumeration {
      enum "not-exist" {
        value 0;
        description
          "The status of the current module package is not-exist.";
      }
      enum "running" {
        value 3;
        description
          "The status of the current module package is running.";
      }
    }
    description
      "Status of the current module package.";
  }
  typedef operation-type { 
    type enumeration {
      enum "install-module" {
        value 0;
        description
          "The operation type of module operation is install-module.";
      }
      enum "uninstall-module" {
        value 1;
        description
          "The operation type of module operation is uninstall-module.";
      }
      enum "startup-module" {
        value 2;
        description
          "The operation type of module operation is startup-module.";
      }
      enum "reset-startup-module" {
        value 3;
        description
          "The operation type of module operation is reset-startup-module.";
      }
    }
    description
      "Specify module operation type.";
  }
  typedef operation-status { 
    type enumeration {
      enum "not-started" {
        value 0;
        description
          "The current status of module operation is not started.";
      }
      enum "operating" {
        value 1;
        description
          "The current status of module operation is operating.";
      }
      enum "successful" {
        value 2;
        description
          "The current status of module operation is successful.";
      }
      enum "failed" {
        value 3;
        description
          "The current status of module operation is failed.";
      }
    }
    description
      "Specify module operation status.";
  }
  typedef schedule-query-type { 
    type enumeration {
      enum "default" {
        value 0;
        description
          "Default mode.";
      }
      enum "hftp" {
        value 1;
        description
          "HFTP mode.";
      }
    }
    description
      "Progress query type.";
  }
  typedef file-type {
    type enumeration {
      enum "module" {
        value 3;
        description
          "Module package.";
      }
    }
    description
      "File type.";
  }
  typedef service-type {
    type enumeration {
      enum "module" {
        value 7;
        description
          "Module file path type.";
      }
    }
    description
      "Service type.";
  }
  typedef action-type {
    type enumeration {
      enum "all" {
        value 0;
        description
          "The action of deleting module package is all.";
      }
      enum "single" {
        value 1;
        description
          "The action of deleting module package is single.";
      }
    }
    description
      "Specify the action of deleting module package.";
  }
  typedef transfer-type {
    type enumeration {
      enum "ftp" {
        value 0;
        description
          "FTP mode.";
      }
      enum "sftp" {
        value 1;
        description
          "SFTP mode.";
      }
    }
    description
      "Transfer type.";
  }
  typedef check-type {
    type enumeration {
      enum "startup" {
        value 0;
        description
          "The action of checking module package is startup module packages.";
      }
      enum "specified-file" {
        value 1;
        description
          "The action of checking module package is a specified module package.";
      }
    }
    description
      "Specify the action of checking module packages.";
  }
  typedef fail-reason { 
    type enumeration {
      enum "file-not-exist" {
        value 0;
        description
          "The failure of module operation is file-not-exist.";
      }
      enum "filename-check-failed" {
        value 1;
        description
          "The failure of module operation is filename-check-failed.";
      }
      enum "integrity-check-failed" {
        value 2;
        description
          "The failure of module operation is integrity-check-failed.";
      }
      enum "file-check-failed" {
        value 3;
        description
          "The failure of module operation is file-check-failed.";
      }
      enum "file-not-match" {
        value 4;
        description
          "The failure of module operation is file-not-match.";
      }
      enum "system-busy" {
        value 5;
        description
          "The failure of module operation is system-busy.";
      }
      enum "insufficient-storage-space" {
        value 6;
        description
          "The failure of module operation is insufficient-storage-space.";
      }
      enum "operation-failed" {
        value 7;
        description
          "The failure of module operation is operation-failed.";
      }
    }
    description
      "Module operation failure.";
  }
  
  typedef transfer-protocol-type {
    type enumeration {
      enum "sftp" {
        value 0;
        description
          "Secure file transfer protocol.";
      }
    }
    description
      "Type of the transfer protocol.";
  }

  typedef plug-package-action-type {
    type enumeration {
      enum "download-and-load-plug-package" {
        value 0;
        description
          "Download and load plug package.";
      }
      enum "activate-plug-package" {
        value 1;
        description
          "Activate plug package.";
      }
      enum "delete-plug-package" {
        value 2;
        description
          "Delete plug package.";
      }
      enum "startup-plug-package" {
        value 3;
        description
          "Set next startup plug package.";
      }
      enum "reset-startup-plug-package" {
        value 4;
        description
          "Reset next startup plug package.";
      }
      enum "none" {
        value 99;
        description
          "Nothing to do.";
      }
    }
    description
      "Plug package action type.";
  }
  typedef status-type {
    type enumeration {
      enum "end" {
        value 0;
        description
          "End.";
      }
      enum "doing" {
        value 1;
        description
          "Doing.";
      }
      enum "start" {
        value 2;
        description
          "Start.";
      }
      enum "fail" {
        value 3;
        description
          "Fail.";
      }
    }
    description
      "Status type.";
  }

  container module-management {
    config false;
    description
      "Module package management.";
    
    container module-infos {
      description
        "List of module packet informations.";
      list module-info {
        key "package-name";
        description
          "Operational data of a module packet information.";
        leaf package-name {
          type string {
            length "5..63";
          }
          description
            "Name of the current module package.";
        }
        leaf version {
          type string {
            length "1..63";
          }
          description
            "Version of the current module package.";
        }
        leaf module-name {
          type string {
            length "1..63";
          }
          description
            "Name of the current module.";
        }

        leaf state {
          type module-state;
          description
            "Status of the current module package.";
        }
        leaf runtime {
          type yang:date-and-time;
          description
            "Run time of the current module package.";
        }
        leaf path {
          type string {
            length "1..127";
          }
          description
            "Path of the current module package.";
        }
      }
    }
    container next-startup-modules {
      description
        "List of next startup module packet informations.";
      list next-startup-module {
        key "name";
        description
          "Operational data of a module startup packet information.";
        leaf name {
          type string {
            length "5..63";
          }
          description
            "Name of a next startup module package.";
        }
        leaf path {
          type string {
            length "1..127";
          }
          description
            "Path of a next startup module package.";
        }
        leaf version {
          type string {
            length "1..63";
          }
          description
            "Version of a next startup module package.";
        }
        leaf module-name {
          type string {
            length "1..63";
          }
          description
            "Module name of a next startup module package.";
        }
        leaf match-status {
          type match-status;
          description
            "Match status of a next startup module package.";
        }
      }
    }
    container operation-schedules {
      description
        "List of module operation process.";
      list operation-schedule {
        key "phase";
        description
          "Operational data of module operation process.";
        leaf phase {
          type operation-type;
          description
            "Module operation type.";
        }
        leaf name {
          type string {
            length "5..63";
          }
          description
            "Name of a module package.";
        }
        leaf status {
          type operation-status;
          description
            "Module operation status.";
        }
        leaf schedule {
          type pub-type:percent;
          description
            "Value of the module operation process.";
        }
		leaf fail-reason {
          when "../status = 'failed'";
          type fail-reason;
          description
            "Cause of the module operation failure.";
        }
      }
    }
  container module-packages {
      config false;
      description
        "List of module packages in user directory.";
      list module-package {
        key "file-name";
        description
          "Operational data of a module package information.";
        leaf file-name {
          type string {
            length "1..255";
          }
          description
            "Name of a module package.";
        }
        leaf module-name {
          type string {
            length "1..63";
          }
          description
            "Module name of a module package.";
        }
        leaf version {
          type string {
            length "1..63";
          }
          description
            "Version of a module package.";
        }
      }
    }
    container download-package-schedule {
      description
        "Operational data of package loading progress.";
      leaf name {
        type string {
          length "1..127";
        }
        description
          "File name.";
      }
      leaf status {
        type operation-status;
        description
          "Package loading status.";
      }
      leaf schedule {
        type pub-type:percent;
        description
          "The schedule of file download, for example, progress (%).";
      }
      leaf transfer-index {
        type uint32;
        description
          "Transfer index.";
      }
      leaf query-type {
        type schedule-query-type;
        description
          "Progress query type.";
      }
    }
    container download-package-load-path {
      description
        "Operational data of load path before downloading a module package.";
      leaf file-type {
        type file-type;
        description
          "File type.";
      }
      leaf service-type {
        type service-type;
        description
          "Service type.";
      }
      leaf file-path {
        type string {
          length "0..128";
        }
        description
          "File path. If the value of file-type node is module, the file path will be /$_install_mod/.";
      }
    }
    container loaded-plug-package-infos {
      description
        "List of the loaded plug package information.";
      list loaded-plug-package-info {
        key "plug-package-version application-type base-version";
        description
          "Operational data of the loaded plug package information.";
        leaf plug-package-version {
          type string {
            length "1..31";
          }
          description
            "Version of the plug package.";
        }
        leaf application-type {
          type string {
            length "1..63";
          }
          description
            "Application type of the plug package.";
        }
        leaf base-version {
          type string {
            length "1..31";
          }
          description
            "Version of base software corresponding to the plug package.";
        }
      }
    }
    container activated-plug-package-version-infos {
      description
        "List of the activated plug package version information.";
      list activated-plug-package-version-info {
        key "plug-package-version application-type base-version";
        description
          "Operational data of the activated plug package version information.";
        leaf plug-package-version {
          type string {
            length "1..31";
          }
          description
            "Version of the plug package.";
        }
        leaf application-type {
          type string {
            length "1..63";
          }
          description
            "Application type of the plug package.";
        }
        leaf base-version {
          type string {
            length "1..31";
          }
          description
            "Version of base software corresponding to the plug package.";
        }
      }
    }
    container next-plug-package-version-infos {
      description
        "List of the plug package version information for next startup.";
      list next-plug-package-version-info {
        key "plug-package-version application-type base-version";
        description
          "Operational data of the plug package version information for next startup.";
        leaf plug-package-version {
          type string {
            length "1..31";
          }
          description
            "Version of the plug package for next startup.";
        }
        leaf application-type {
          type string {
            length "1..63";
          }
          description
            "Application type of the plug package for next startup.";
        }
        leaf base-version {
          type string {
            length "1..31";
          }
          description
            "Version of base software corresponding to the plug package for next startup.";
        }
      }
    }
    container plug-package-action-results {
      description
        "List of the plug package action results.";
      list plug-package-action-result {
        key "command";
        description
          "Operational data of the plug package action results.";
        leaf command {
          type plug-package-action-type;
          description
            "Command of the action.";
        }
        leaf action-start-time {
          type yang:date-and-time;
          description
            "Start time of the action.";
        }
        leaf action-end-time {
          type yang:date-and-time;
          description
            "End time of the action.";
        }
        leaf action-status {
          type status-type;
          description
            "Status of the action.";
        }
        leaf action-progress {
          type pub-type:percent;
          description
            "Progress of the action.";
        }
      }
    }
  }

  rpc install-module {
    ext:node-ref "/file-operation:file-operation/file-operation:dirs/file-operation:dir";
    description
      "Load a module package.";
    input {
      leaf name {
        type string {
          length "5..63";
        }
        mandatory true;
        description
          "Name of a module package.";
      }
    }
  }
  rpc uninstall-module {
    description
      "Delete a module package.";
    ext:node-ref "/module-management/module-infos/module-info";
    input {
      leaf action-type {
        type action-type;
        default "single";
        description
          "Specify the action of uninstall module package.";
      }
      leaf name {
        when "../action-type != 'all'";
        type leafref {
          path "/module-management/module-infos/module-info/package-name";
        }
        description
          "Name of a module package.";
      }
    }
  }
  rpc startup-module {
    ext:node-ref "/file-operation:file-operation/file-operation:dirs/file-operation:dir";
    description
      "Specify the module package that will be used at the next startup.";
    input {
      leaf name {
        type string {
          length "5..63";
        }
        mandatory true;
        description
          "Specify the name of a module package that will be used at the next startup.";
      }
    }
  }
  rpc reset-startup-module {
    description
      "Delete a module packet that will be used at the next startup.";
    ext:node-ref "/module-management/next-startup-modules/next-startup-module";
    input {
      leaf action-type {
        type action-type;
        default "single";
        description
          "Specify the action of reset startup module package.";
      }
      leaf name {
        when "../action-type != 'all'";
        type leafref {
          path "/module-management/next-startup-modules/next-startup-module/name";
        }
        description
          "Specify the name of a module package that used at the next startup.";
      }
    }
  }
  rpc download-module-file {
    description
      "Download module package.";
    input {
      leaf server-ip {
        type inet:ipv4-address-no-zone;
        mandatory true;
        description
          "Server address.";
      }
      leaf user-name {
        type string {
          length "1..255";
        }
        mandatory true;
        description
          "User name.";
      }
      leaf password {
        type pub-type:password-extend {
            length "1..255";
        }
        mandatory true;
        description
          "Password of FTP or SFTP server.";
      }
      leaf server-port {
        type uint32 {
          range "1..65535";
        }
        mandatory true;
        description
          "Server port.";
      }
      leaf file-name {
        type string {
          length "5..128";
        }
        mandatory true;
        description
          "Package name.";
      }
      leaf transfer-type {
        type transfer-type;
        description
          "Transfer type.";
      }
    }
  }
  rpc check-module {
    description
      "Check module packages.";
    input {
      leaf check-type {
        type check-type;
        mandatory true;
        description
          "Specify the action of check startup module packages.";
      }
      leaf name {
        when "../check-type != 'startup'";
        type string {
          length "5..127";
        }
        mandatory true;
        description
          "Name of a module package.";
      }
    }
    output {
      container result-infos {
        description
          "List of checking module package result.";
        list result-info {
          key "name";
          description
            "Result information of check module packages.";
          leaf name {
            type string {
              length "5..127";
            }
            description
              "Name of a module package.";
          }
          leaf result {
            type string {
              length "1..255";
            }
            description
              "Result of check a module package.";
          }
        }
      }
    }
  }
  rpc download-and-load-plug-package {
    description
      "Download and load the plug package.";
    input {
      leaf server-ip {
        type inet:ipv4-address-no-zone;
        mandatory true;
        description
          "Specify the IP address of the download server.";
      }
      leaf server-port {
        type uint32 {
          range "0..65535";
        }
        mandatory true;
        description
          "Specify the port number of the download server.";
      }
      leaf user-name {
        type string{
          length "1..63";
        }
        mandatory true;
        description
          "Specify the user name.";
      }
      leaf password {
        type pub-type:password {
            length "1..127";
        }
        mandatory true;
        description
          "Specify the password.";
      }
      leaf plug-package-directory {
        type string {
            length "1..255";
        }
        mandatory true;
        description
          "Specify the directory of the plug package on the server.";
      }
      leaf plug-package-name {
        type string {
            length "1..255";
        }
        mandatory true;
        description
          "Specify the name of the plug package on the server.";
      }
      leaf transfer-protocol {
        type transfer-protocol-type;
        default "sftp";
        description
          "Specify the transfer protocol.";
      }
    }
  }
  rpc activate-plug-package {
    description
      "Activate the plug package.";
    input {
      leaf application-type {
        type string {
          length "1..63";
        }
        mandatory true;
        description
          "Specify the application type of the plug package to be activated.";
      }
      leaf plug-package-version {
        type string {
          length "1..31";
        }
        mandatory true;
        description
          "Specify the version of the plug package to be activated.";
      }
    }
  }
  rpc delete-plug-package {
    description
      "Delete the plug package.";
    input {
      leaf application-type {
        type string {
          length "1..63";
        }
        mandatory true;
        description
          "Specify the application type of the plug package to be deleted.";
      }
    }
  }
  rpc startup-plug-package {
    description
      "Set the plug package for next startup.";
    input {
      leaf application-type {
        type string {
          length "1..63";
        }
        mandatory true;
        description
          "Specify the application type of the plug package to be set for next startup.";
      }
      leaf plug-package-version {
        type string {
          length "1..31";
        }
        mandatory true;
        description
          "Specify the version of the plug package to be set for next startup.";
      }
      leaf base-version {
        type string {
          length "1..31";
        }
        mandatory true;
        description
          "Specify the version of the base software to be set for next startup.";
      }
    }
  }
  rpc reset-startup-plug-package {
    description
      "Reset the plug package for next startup.";
    input {
      leaf application-type {
        type string {
          length "1..63";
        }
        mandatory true;
        description
          "Specify the application type of the plug package to be reset for next startup.";
      }
      leaf base-version {
        type string {
          length "1..31";
        }
        mandatory true;
        description
          "Specify the version of the base software to be reset for next startup.";
      }
    }
  }
}
