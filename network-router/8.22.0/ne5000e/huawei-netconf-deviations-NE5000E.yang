/*
Copyright (C) 2021 Huawei Technologies Co., Ltd. All rights reserved.
*/
module huawei-netconf-deviations-NE5000E {
  namespace "urn:huawei:yang:huawei-netconf-deviations-NE5000E";
  prefix netconf-devs-NE5000E;

  import huawei-netconf {
    prefix netconf;
  }

  organization
    "Huawei Technologies Co., Ltd.";
  contact
    "Huawei Industrial Base
     Bantian, Longgang
     Shenzhen 518129
     People's Republic of China
     Website: http://www.huawei.com
     Email: support@huawei.com";
  description
    "This module defines deviation statements for huawei-netconf module.";

  revision 2021-05-07 {
    description
      "Initial revision.";
    reference "Huawei private.";
  }

  deviation "/netconf:netconf/netconf:config-cache" {
    deviate not-supported;
  }
}
