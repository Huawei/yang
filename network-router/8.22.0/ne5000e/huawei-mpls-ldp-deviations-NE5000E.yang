/*
Copyright (C) 2021 Huawei Technologies Co., Ltd. All rights reserved.
*/
module huawei-mpls-ldp-deviations-NE5000E {
  namespace "urn:huawei:yang:huawei-mpls-ldp-deviations-NE5000E";
  prefix mpls-ldp-devs-NE5000E;

  import huawei-mpls-ldp {
    prefix mpls-ldp;
  }
  import huawei-mpls {
    prefix mpls;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-mpls-ldp module.";

  revision 2021-05-07 {
    description
      "Initial revision.";
    reference "Huawei private.";
  }

  typedef ldp-peer-group-auth-mode-deviations {
    type enumeration {
      enum md5 {
        value 1;
        description
          "Specifies mode for cipher or plain MD5 password.";
      }
      enum keychain {
        value 2;
        description
          "Specifies mode for keychain password.";
      }
    }
    description
      "LDP Peer Authentication Type.";
  }

  deviation "/mpls:mpls/mpls-ldp:ldp/mpls-ldp:global/mpls-ldp:entropy-label-enable" {
    deviate not-supported;
  }
  deviation "/mpls:mpls/mpls-ldp:ldp/mpls-ldp:global/mpls-ldp:bit-err-detect-level" {
    deviate not-supported;
  }
  deviation "/ni:network-instance/ni:instances/ni:instance/mpls:mpls/mpls-ldp:ldp/mpls-ldp:instance/mpls-ldp:auto-dod-request-enable" {
    deviate not-supported;
  }
  deviation "/ni:network-instance/ni:instances/ni:instance/mpls:mpls/mpls-ldp:ldp/mpls-ldp:instance/mpls-ldp:label-ctrl-mode" {
    deviate not-supported;
  }
  deviation "/ni:network-instance/ni:instances/ni:instance/mpls:mpls/mpls-ldp:ldp/mpls-ldp:instance/mpls-ldp:interfaces/mpls-ldp:interface/mpls-ldp:label-advertise-mode" {
    deviate not-supported;
  }
  deviation "/ni:network-instance/ni:instances/ni:instance/mpls:mpls/mpls-ldp:ldp/mpls-ldp:instance/mpls-ldp:remote-peers/mpls-ldp:remote-peer/mpls-ldp:auto-dod-request-mode" {
    deviate not-supported;
  }
  deviation "/ni:network-instance/ni:instances/ni:instance/mpls:mpls/mpls-ldp:ldp/mpls-ldp:instance/mpls-ldp:remote-peers/mpls-ldp:remote-peer/mpls-ldp:label-advertise-mode" {
    deviate not-supported;
  }
  deviation "/ni:network-instance/ni:instances/ni:instance/mpls:mpls/mpls-ldp:ldp/mpls-ldp:instance/mpls-ldp:peer-infos/mpls-ldp:peer-info/mpls-ldp:iccp-capability" {
    deviate not-supported;
  }
  deviation "/ni:network-instance/ni:instances/ni:instance/mpls:mpls/mpls-ldp:ldp/mpls-ldp:instance/mpls-ldp:sessions/mpls-ldp:session/mpls-ldp:iccp-capability" {
    deviate not-supported;
  }
  deviation "/mpls:mpls/mpls-ldp:ldp/mpls-ldp:bfd/mpls-ldp:p2p/mpls-ldp:min-tx" {
    deviate replace {
      type uint32 {
        range "10..1000";
      }
    }
  }
  deviation "/mpls:mpls/mpls-ldp:ldp/mpls-ldp:bfd/mpls-ldp:p2p/mpls-ldp:min-rx" {
    deviate replace {
      type uint32 {
        range "10..1000";
      }
    }
  }
  deviation "/mpls:mpls/mpls-ldp:ldp/mpls-ldp:bfd/mpls-ldp:mldp/mpls-ldp:p2mp-tunnel-min-tx" {
    deviate replace {
      type uint32 {
        range "10..1000";
      }
    }
  }
  deviation "/ni:network-instance/ni:instances/ni:instance/mpls:mpls/mpls-ldp:ldp/mpls-ldp:instance/mpls-ldp:remote-peers/mpls-ldp:remote-peer/mpls-ldp:status/mpls-ldp:manual-configuration-effect" {
    deviate add {
      default "false";
    }
  }
  deviation "/ni:network-instance/ni:instances/ni:instance/mpls:mpls/mpls-ldp:ldp/mpls-ldp:instance/mpls-ldp:auth-peer-groups/mpls-ldp:auth-peer-group/mpls-ldp:authen-mode" {
    deviate replace {
      type mpls-ldp-devs-NE5000E:ldp-peer-group-auth-mode-deviations;
    }
  }
}
