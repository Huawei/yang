/*
Copyright (C) 2021 Huawei Technologies Co., Ltd. All rights reserved.
*/
module huawei-ifm-notification-deviations-NE5000E {
  namespace "urn:huawei:yang:huawei-ifm-notification-deviations-NE5000E";
  prefix ifm-notification-devs-NE5000E;

  import huawei-ifm-notification {
    prefix ifm-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-ifm-notification module.";

  revision 2021-05-07 {
    description
      "Initial revision.";
    reference "Huawei private.";
  }

  deviation "/ifm-notification:error-down" {
    deviate not-supported;
  }
  deviation "/ifm-notification:error-down-recovery" {
    deviate not-supported;
  }
  deviation "/ifm-notification:physical-admin-if-down" {
    deviate not-supported;
  }
  deviation "/ifm-notification:physical-admin-if-up" {
    deviate not-supported;
  }
  deviation "/ifm-notification:if-ipv4-conflict" {
    deviate not-supported;
  }
  deviation "/ifm-notification:if-ipv4-conflict-resume" {
    deviate not-supported;
  }
}
