/*
Copyright (C) 2021 Huawei Technologies Co., Ltd. All rights reserved.
*/
module huawei-l2vpn-vll-ext-deviations-NE5000E {
  namespace "urn:huawei:yang:huawei-l2vpn-vll-ext-deviations-NE5000E";
  prefix l2vpn-vll-ext-devs-NE5000E;

  import huawei-l2vpn-vll-ext {
    prefix l2vpn-vll-ext;
  }

  import huawei-ifm {
    prefix ifm;
  }

  import huawei-qos {
    prefix qos;
  }

  organization
    "Huawei Technologies Co., Ltd.";

  contact
    "Huawei Industrial Base
     Bantian, Longgang
     Shenzhen 518129
     People's Republic of China
     Website: http://www.huawei.com
     Email: support@huawei.com";

  description
    "This module defines deviation statements for huawei-l2vpn-vll-ext module.";

  revision 2021-05-07 {
    description
      "Initial revision.";
    reference
      "Huawei private.";
  }

  deviation "/ifm:ifm/ifm:interfaces/ifm:interface/l2vpn-vll-ext:vll-pw-loop-check" {
    deviate not-supported;
  }
  deviation "/ifm:ifm/ifm:interfaces/ifm:interface/l2vpn-vll-ext:encapsulation-vlan" {
    deviate not-supported;
  }
  deviation "/ifm:ifm/ifm:interfaces/ifm:interface/l2vpn-vll-ext:l2vpn-migration" {
    deviate not-supported;
  }
  deviation "/ifm:ifm/ifm:interfaces/ifm:interface/qos:qos/l2vpn-vll-ext:qos-vll-pipe/l2vpn-vll-ext:split-mode" {
    deviate delete {
      must "((../split-mode='false') or (../split-mode='true' and not(../ingress-pipe-mode='uniform' and ../egress-pipe-mode='uniform')))";
    }
    deviate add {
      must "(../split-mode='false')";
    }
  }

}
