/*
Copyright (C) 2021 Huawei Technologies Co., Ltd. All rights reserved.
*/
module huawei-soc-notification-deviations-NE5000E {
  namespace "urn:huawei:yang:huawei-soc-notification-deviations-NE5000E";
  prefix soc-notification-devs-NE5000E;

  import huawei-soc-notification {
    prefix soc-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-soc-notification module.";

  revision 2021-05-07 {
    description
      "Initial revision.";
    reference
      "Huawei private.";
  }

  deviation "/soc-notification:l2-loop-detect-alarm" {
    deviate not-supported;
  }
  deviation "/soc-notification:l2-loop-detect-alarm-clear" {
    deviate not-supported;
  }
  deviation "/soc-notification:access-rate-remains-low" {
    deviate not-supported;
  }
  deviation "/soc-notification:access-rate-remains-low-clear" {
    deviate not-supported;
  }

}
