/*
Copyright (C) 2021 Huawei Technologies Co., Ltd. All rights reserved.
*/
module huawei-crypto-deviations-NE5000E {
  namespace "urn:huawei:yang:huawei-crypto-deviations-NE5000E";
  prefix crypto-devs-NE5000E;

  import huawei-crypto {
    prefix crypto;
  }

  organization
    "Huawei Technologies Co., Ltd.";
  contact
    "Huawei Industrial Base
     Bantian, Longgang
     Shenzhen 518129
     People's Republic of China
     Website: http://www.huawei.com
     Email: support@huawei.com";
  description
    "This module defines deviation statements for huawei-crypto module.";

  revision 2021-05-07 {
    description
      "Initial revision.";
    reference "Huawei private.";
  }

  deviation "/crypto:crypto/crypto:fips-mode" {
    deviate not-supported;
  }
  deviation "/crypto:crypto/crypto:weak-algorithm" {
    deviate not-supported;
  }
}
