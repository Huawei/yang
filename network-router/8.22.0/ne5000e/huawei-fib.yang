/*
Copyright (C) 2019-2022 Huawei Technologies Co., Ltd. All rights reserved.
*/
module huawei-fib {
  yang-version 1;
  namespace "urn:huawei:yang:huawei-fib";
  prefix fib;
  import huawei-network-instance {
    prefix ni;
  }
  import huawei-pub-type {
    prefix pub-type;
  }
  import ietf-inet-types {
    prefix inet;
  }
  import huawei-extension {
    prefix ext;
  }
  import huawei-devm {
    prefix devm;
  }
  organization
    "Huawei Technologies Co., Ltd.";
  contact
    "Huawei Industrial Base
    Bantian, Longgang
    Shenzhen 518129
    People's Republic of China
    Website: http://www.huawei.com
    Email: support@huawei.com";
  description
    "Forwarding information base.";
  revision 2022-09-23 {
    description
      "Modify Node.";
    reference
      "Huawei private.";
  }
  revision 2020-03-06 {
    description
      "Modify description.";
    reference
      "Huawei private.";
  }
  revision 2019-04-01 {
    description
      "Initial revision.";
    reference
      "Huawei private.";
  }
  typedef af-type {
    type enumeration {
      enum "ipv4unicast" {
        value 1;
        description
          "IPv4 address family type.";
      }
      enum "ipv6unicast" {
        value 2;
        description
          "IPv6 address family type.";
      }
    }
    description
      "Af type.";
  }
  typedef fib-cfg-type {
    type enumeration {
      enum "ipv4-fib" {
        value 1;
        description
          "IPv4 FIB type.";
      }
      enum "ipv6-fib" {
        value 2;
        description
          "IPv6 FIB type.";
      }
    }
    description
      "FIB type.";
  }
  ext:task-name "forwarding";
  container fib {
    description
      "Forwarding information base.";
    container unicast-afs {
      config false;
      description
        "List of forwarding information base.";
      list unicast-af {
        key "vrf-name af-type position";
        description
          "Operational state of forwarding information base.";
        leaf vrf-name {
          type leafref {
            path "/ni:network-instance/ni:instances/ni:instance/ni:name";
          }
          description
            "Virtual private network.";
        }
        leaf af-type {
          type af-type;
          description
            "Address type.";
        }
        leaf position {
          type string {
            length "0..16";
          }
          description
            "Slot number.";
        }
        container routes {
          description
            "List of FIB entry.";
          list route {
            key "destination mask nexthop if-name tunnel-id";
            description
              "Operational state of FIB entry.";
            leaf destination {
              type inet:ip-address-no-zone;
              description
                "Destination address.";
            }
            leaf mask {
              type uint32 {
                range "0..128";
              }
              description
                "The length of mask address.";
            }
            leaf nexthop {
              type inet:ip-address-no-zone;
              description
                "Next hop address.";
            }
            leaf if-name {
              type pub-type:if-name;
              description
                "Interface name.";
            }
            leaf tunnel-id {
              type string {
                length "0..49";
              }
              description
                "Tunnel ID.";
            }
            leaf vlan-id {
              type uint32;
              description
                "VLAN ID.";
            }
            leaf inner-label {
              type pub-type:hex-binary;
              description
                "Inner label.";
            }
            leaf lsp-token {
              type pub-type:hex-binary;
              description
                "The token of label switch path.";
            }
            leaf bak-nexthop {
              type inet:ip-address-no-zone;
              description
                "Backup next hop address.";
            }
            leaf bak-if-name {
              type pub-type:if-name;
              description
                "Backup interface name.";
            }
            leaf bak-inner-lable {
              type pub-type:hex-binary;
              description
                "Backup inner label.";
            }
            leaf bak-lsp-token {
              type pub-type:hex-binary;
              description
                "Backup LSP token.";
            }
          }
        }
        container statistics {
          description
            "FIB total number statistics.";
          leaf total-num {
            type uint32;
            description
              "FIB total number.";
          }
        }
      }
    }
  }
  augment "/devm:devm/devm:lpu-boards/devm:lpu-board" {
    description
      "Configure FIB to the devm module.";
    container fib {
      description
        "Configure FIB.";
      container fib-alarm-thresholds {
        description
          "List of user-defined FIB alarm threshold.";
        list fib-alarm-threshold {
          must "upper-limit>lower-limit";
          key "fib-type";
          description
            "Configure user-defined FIB alarm threshold.";
          leaf fib-type {
            type fib-cfg-type;
            description
              "FIB type.";
          }
          leaf lower-limit {
            type uint32 {
              range "1..99";
            }
            mandatory true;
            description
              "User-defined lower-limit of FIB alarm threshold.";
          }
          leaf upper-limit {
            type uint32 {
              range "2..100";
            }
            mandatory true;
            description
              "User-defined upper-limit of FIB alarm threshold.";
          }
        }
      }
      container fib-capacity-limits {
        description
          "List of user-defined FIB capacity limit.";
        list fib-capacity-limit {
          key "fib-type";
          description
            "Configure user-defined FIB capacity limit.";
          leaf fib-type {
            type fib-cfg-type;
            description
              "FIB type.";
          }
          leaf capacity-limit {
            type uint32 {
              range "1..4294967295";
            }
            mandatory true;
            description
              "User-defined FIB capacity-limit. The configured FIB capacity must be less than or equal to the FIB capacity of the board and greater than or equal to the number of used FIB entries on the board.";
          }
        }
      }
    }
  }
  augment "/devm:devm/devm:mpu-boards/devm:mpu-board" {
    description
      "Configure FIB to the devm module.";
    container fib {
      description
        "Configure FIB.";
      container fib-alarm-thresholds {
        description
          "List of user-defined FIB alarm threshold.";
        list fib-alarm-threshold {
          must "upper-limit>lower-limit";
          key "fib-type";
          description
            "Configure user-defined FIB alarm threshold.";
          leaf fib-type {
            type fib-cfg-type;
            description
              "FIB type.";
          }
          leaf lower-limit {
            type uint32 {
              range "1..99";
            }
            mandatory true;
            description
              "User-defined lower-limit of FIB alarm threshold.";
          }
          leaf upper-limit {
            type uint32 {
              range "2..100";
            }
            mandatory true;
            description
              "User-defined upper-limit of FIB alarm threshold.";
          }
        }
      }
      container fib-capacity-limits {
        description
          "List of user-defined FIB capacity limit.";
        list fib-capacity-limit {
          key "fib-type";
          description
            "Configure user-defined FIB capacity limit.";
          leaf fib-type {
            type fib-cfg-type;
            description
              "FIB type.";
          }
          leaf capacity-limit {
            type uint32 {
              range "1..4294967295";
            }
            mandatory true;
            description
              "User-defined FIB capacity-limit. The configured FIB capacity must be less than or equal to the FIB capacity of the board and greater than or equal to the number of used FIB entries on the board.";
          }
        }
      }
    }
  }
}
