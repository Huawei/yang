/*
Copyright (C) 2019-2022 Huawei Technologies Co., Ltd. All rights reserved.
*/
module huawei-cfg-ext {
  yang-version 1.1;
  namespace "urn:huawei:yang:huawei-cfg-ext";
  prefix cfg-ext;
  import huawei-extension {
    prefix ext;
  }
  import huawei-cfg {
    prefix cfg;
  }
  organization
    "Huawei Technologies Co., Ltd.";
  contact
    "Huawei Industrial Base
    Bantian, Longgang
    Shenzhen 518129
    People's Republic of China
    Website: http://www.huawei.com
    Email: support@huawei.com";
  description
    "Display the changes information in the candidate datastore.";
  revision 2022-03-25 {
   description
      "Change commit-id type to leafref.";
   reference
      "Huawei private.";
  }
  revision 2019-05-21 {
    description
      "Init revision.";
    reference
      "RFC 6241, Section 8.3.";
  }
  ext:task-name "config";
  rpc get-candidate-change {
    description
      "Configuration change information.";
    output  {
      anydata effective-changes {
        description
          "Configuration change information recorded in the candidate datastore.";
      }
      anydata ineffective-changes {
        description
          "Changes in configurations that have not taken effect in the candidate datastore.";
      }
    }
  }
  rpc get-configuration-change {
    description "Get configuration change information.";
    input  {
      container source {
        description "The source configuration.";
        choice config-source {
           description "Particular source configuration to compare from.";
          case checkpoint {
            description "Configuration checkpoints.";
            leaf commit-id {
              type leafref {
               path "/cfg:cfg/cfg:checkpoints/cfg:checkpoint/cfg:commit-id";
              }
              description "Uniquely identify a configuration checkpoint.";
            }
          }
          case running {
            description "Running configuration.";
            leaf running {
              type empty;
              description "Running configuration.";
            }
          }
          case url {
            description "The URL-based configuration.";
            leaf url {
              type string {
              length "1..256";
              }
              description "The URL-based configuration.";
            }
          }
        }
      }
      container target{
        description "The target configuration.";
        choice config-target {
          description "Particular target configuration to compare to.";
          case checkpoint {
            description "Configuration checkpoints.";
            leaf commit-id {
              type leafref {
               path "/cfg:cfg/cfg:checkpoints/cfg:checkpoint/cfg:commit-id";
              }
              description "Uniquely identify a configuration checkpoint.";
            }
          }
          case running {
            description "Running configuration.";
            leaf running {
              type empty;
              description "Running configuration.";
            }
          }
          case url {
            description "The URL-based configuration.";
            leaf url {
              type string {
              length "1..256";
              }
              description "The URL-based configuration.";
            }
          }
        }
      }
      leaf rollback-tag {
        type empty;
        description "With rollback tag.";
      }
    }
    output  {
      anydata changes {
        description
          "Configuration changes.";
      }
    }
  }
  rpc load-configuration-change {
    description
    "After configuration difference loading, users can get to know the result of configuration difference loading through load-configuration-result node.";
    input  {
      anydata changes {
        description
          "Configuration change to be loaded.";
      }
    }
  }
  rpc load-configuration-result {
    description
      "The result of load configuration changes.";
    output  {
      anydata result {
        description
          "Configuration loading result.";
      }
    }
  }
}
