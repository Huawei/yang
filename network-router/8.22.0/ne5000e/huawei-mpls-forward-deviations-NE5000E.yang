/*
Copyright (C) 2021 Huawei Technologies Co., Ltd. All rights reserved.
*/
module huawei-mpls-forward-deviations-NE5000E {
  namespace "urn:huawei:yang:huawei-mpls-forward-deviations-NE5000E";
  prefix mpls-forward-devs-NE5000E;

  import huawei-mpls-forward {
    prefix mpls-forward;
  }

  import huawei-ifm {
    prefix ifm;
  }

  import huawei-loadbalance {
    prefix loadbalance;
  }

  import huawei-mpls {
    prefix mpls;
  }

  organization
    "Huawei Technologies Co., Ltd.";

  contact
    "Huawei Industrial Base
     Bantian, Longgang
     Shenzhen 518129
     People's Republic of China
     Website: http://www.huawei.com
     Email: support@huawei.com";

  description
    "This module defines deviation statements for huawei-mpls-forward module.";

  revision 2021-05-07 {
    description
      "Initial revision.";
    reference
      "Huawei private.";
  }

  deviation "/loadbalance:loadbalance/mpls-forward:mpls-hashpacket" {
    deviate not-supported;
  }
  deviation "/loadbalance:loadbalance/mpls-forward:mpls-intfmtu" {
    deviate not-supported;
  }
  deviation "/loadbalance:loadbalance/mpls-forward:mpls-loadblc-elawords" {
    deviate not-supported;
  }
  deviation "/ifm:ifm/ifm:interfaces/ifm:interface/mpls-forward:if-p2mp-load-balance/mpls-forward:root-loadbanlance-enable" {
    deviate not-supported;
  }
  deviation "/ifm:ifm/ifm:interfaces/ifm:interface/mpls-forward:if-p2mp-load-balance/mpls-forward:root-loadbanlance-spmsidis" {
    deviate not-supported;
  }
  deviation "/ifm:ifm/ifm:interfaces/ifm:interface/mpls-forward:bgp-localifnet-traffic" {
    deviate not-supported;
  }
  deviation "/mpls:mpls/mpls-forward:ds-enhance" {
    deviate not-supported;
  }
  deviation "/mpls:mpls/mpls-forward:p2mp-fastswitch" {
    deviate not-supported;
  }
  deviation "/mpls:mpls/mpls-forward:te-reverse-path-forwarding" {
    deviate not-supported;
  }
  deviation "/mpls:mpls/mpls-forward:bgp-separate" {
    deviate not-supported;
  }
  deviation "/mpls:mpls/mpls-forward:ldp-separate" {
    deviate not-supported;
  }
  deviation "/mpls:mpls/mpls-forward:te-multiprot" {
    deviate not-supported;
  }
  deviation "/mpls:mpls/mpls-forward:disp-convergence-mode" {
    deviate not-supported;
  }
  deviation "/mpls:mpls/mpls:common/mpls:global/mpls-forward:entropy-label-mode" {
    deviate not-supported;
  }
  deviation "/mpls:mpls/mpls:common/mpls-forward:mpls-forward" {
    deviate not-supported;
  }

}
