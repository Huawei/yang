/*
Copyright (C) 2021 Huawei Technologies Co., Ltd. All rights reserved.
*/
module huawei-lldp-notification-deviations-NE5000E {
  namespace "urn:huawei:yang:huawei-lldp-notification-deviations-NE5000E";
  prefix lldp-notification-devs-NE5000E;

  import huawei-lldp-notification {
    prefix lldp-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-lldp-notification module.";

  revision 2021-05-07 {
    description
      "Initial revision.";
    reference "Huawei private.";
  }

  deviation "/lldp-notification:lldp-mdn-port-neighbor-changed" {
    deviate not-supported;
  }
}
