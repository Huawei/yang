/*
Copyright (C) 2019 Huawei Technologies Co., Ltd. All rights reserved.
*/
module huawei-netstream-deviations-ATN-980B {
  namespace "urn:huawei:yang:huawei-netstream-deviations-ATN-980B";
  prefix netstream-devs-ATN-980B;

  import huawei-netstream {
    prefix netstream;
  }

  import huawei-extension {
    prefix ext;
  }

  import huawei-ifm {
    prefix ifm;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-netstream module.";

  revision 2019-11-06 {
    description
      "Initial revision.";
    reference
      "Huawei private.";
  }

  typedef nsm-flow-type-deviations {
    type enumeration {
      enum "ip-flow" {
        value 0;
        description 
          "IPv4.";
      }
    }
    description 
      "Netstream flow type deviations.";
  }

  deviation "/netstream:netstream/netstream:flow-instances/netstream:flow-instance/netstream:ttl-flag" {
    deviate not-supported;
  }
  deviation "/netstream:netstream/netstream:flow-instances/netstream:flow-instance/netstream:srv6-aware" {
    deviate not-supported;
  }
  deviation "/netstream:netstream/netstream:flow-instances/netstream:flow-instance/netstream:record-name" {
    deviate not-supported;
  }
  deviation "/netstream:netstream/netstream:monitors/netstream:monitor/netstream:record-name" {
    deviate not-supported;
  }
  deviation "/netstream:netstream/netstream:flexflow-records" {
    deviate not-supported;
  }
  deviation "/netstream:netstream/netstream:sampler-rate-lower-limits" {
    deviate not-supported;
  }
  deviation "/netstream:netstream/netstream:log-enable" {
    deviate not-supported;
  }
  deviation "/netstream:netstream/netstream:stream-log-infos" {
    deviate not-supported;
  }
  deviation "/devm:devm/devm:lpu-boards/devm:lpu-board/netstream:netstream" {
    deviate not-supported;
  }
  deviation "/devm:devm/devm:mpu-boards/devm:mpu-board/netstream:netstream" {
    deviate not-supported;
  }
  deviation "/netstream:netstream/netstream:flow-instances/netstream:flow-instance/netstream:flow-type" {
    deviate replace {
      type netstream-devs-ATN-980B:nsm-flow-type-deviations;
    }
  }
  ext:deviation-ext "/netstream:netstream/netstream:flow-instances/netstream:flow-instance/netstream:export-version" {
    ext:deviate-ext add {
      ext:dynamic-default {
        ext:default-value "5" {
          when "../flow-type='ip-flow'";
          description "The default value is 5 of version when flow type is IPv4.";
        }
      }
    }
  }
  deviation "/netstream:netstream/netstream:aggregations/netstream:aggregation/netstream:flow-type" {
    deviate replace {
      type netstream-devs-ATN-980B:nsm-flow-type-deviations;
    }
  }
  deviation "/netstream:netstream/netstream:monitors/netstream:monitor/netstream:flow-type" {
    deviate replace {
      type netstream-devs-ATN-980B:nsm-flow-type-deviations;
    }
  }
  deviation "/ifm:ifm/ifm:interfaces/ifm:interface/netstream:netstream/netstream:sampler-enables/netstream:sampler-enable" {
    deviate add {
      must "../../../ifm:type='Ethernet' or
../../../ifm:type='GigabitEthernet' or
../../../ifm:type='Eth-Trunk' or
../../../ifm:type='100GE' or
../../../ifm:type='400GE' or
../../../ifm:type='40GE' or
../../../ifm:type='50GE' or
../../../ifm:type='50|100GE' or
../../../ifm:type='25GE' or
../../../ifm:type='ATM' or
../../../ifm:type='FlexE' or
../../../ifm:type='Serial' or
../../../ifm:type='Ip-Trunk' or
../../../ifm:type='Mp-group' or
../../../ifm:type='Pos' or
../../../ifm:type='Vbdif' or
../../../ifm:type='Vlanif' or
(../../../ifm:type='Global-VE' and ../../../ifm:class='sub-interface') or
(../../../ifm:type='Virtual-Ethernet' and ../../../ifm:class='sub-interface')";
    }
  }
  deviation "/ifm:ifm/ifm:interfaces/ifm:interface/netstream:netstream/netstream:sampler-enables/netstream:sampler-enable/netstream:flow-type" {
    deviate replace {
      type netstream-devs-ATN-980B:nsm-flow-type-deviations;
    }
  }
  deviation "/ifm:ifm/ifm:interfaces/ifm:interface/netstream:netstream/netstream:sampler-rates/netstream:sampler-rate" {
    deviate add {
      must "../../../ifm:type='Ethernet' or
../../../ifm:type='GigabitEthernet' or
../../../ifm:type='Eth-Trunk' or
../../../ifm:type='100GE' or
../../../ifm:type='400GE' or
../../../ifm:type='40GE' or
../../../ifm:type='50GE' or
../../../ifm:type='50|100GE' or
../../../ifm:type='25GE' or
../../../ifm:type='ATM' or
../../../ifm:type='FlexE' or
../../../ifm:type='Serial' or
../../../ifm:type='Ip-Trunk' or
../../../ifm:type='Mp-group' or
../../../ifm:type='Pos' or
../../../ifm:type='Vbdif' or
../../../ifm:type='Vlanif' or
(../../../ifm:type='Global-VE' and ../../../ifm:class='sub-interface') or
(../../../ifm:type='Virtual-Ethernet' and ../../../ifm:class='sub-interface')";
    }
  }
  deviation "/ifm:ifm/ifm:interfaces/ifm:interface/netstream:netstream/netstream:mpls-exclude" {
    deviate not-supported;
  }
  deviation "/ifm:ifm/ifm:interfaces/ifm:interface/netstream:netstream/netstream:sampler-rates/netstream:sampler-rate/netstream:flow-type" {
    deviate replace {
      type netstream-devs-ATN-980B:nsm-flow-type-deviations;
    }
  }
  deviation "/ifm:ifm/ifm:interfaces/ifm:interface/netstream:netstream/netstream:statistics-enable/netstream:flow-type" {
    deviate replace {
      type netstream-devs-ATN-980B:nsm-flow-type-deviations;
    }
  }

}
