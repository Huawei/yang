/*
Copyright (C) 2021 Huawei Technologies Co., Ltd. All rights reserved.
*/
module huawei-bras-ipv4-address-manage-deviations-ATN-980B {
  namespace "urn:huawei:yang:huawei-bras-ipv4-address-manage-deviations-ATN-980B";
  prefix bras-ipv4-address-manage-devs-ATN-980B;

  import huawei-bras-ipv4-address-manage {
    prefix bras-ipv4-address-manage;
  }

  import huawei-bras-cu-controller {
    prefix bras-cu-controller;
  }

  import huawei-l3vpn {
    prefix l3vpn;
  }

  import huawei-network-instance {
    prefix ni;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-ipv4-address-manage module.";

  revision 2021-05-07 {
    description
      "Initial revision.";
    reference
      "Huawei private.";
  }

  deviation "/bras-ipv4-address-manage:bras-ipv4-address-manage" {
    deviate not-supported;
  }
  deviation "/bras-ipv4-address-manage:reserved-ip-address" {
    deviate not-supported;
  }
  deviation "/bras-ipv4-address-manage:recycle-subnet" {
    deviate not-supported;
  }
  deviation "/bras-ipv4-address-manage:clear-auto-block" {
    deviate not-supported;
  }
  deviation "/bras-ipv4-address-manage:reset-ip-address" {
    deviate not-supported;
  }
  deviation "/bras-ipv4-address-manage:recycle-ip-address" {
    deviate not-supported;
  }
  deviation "/bras-ipv4-address-manage:reset-ip-pool-ratio-info" {
    deviate not-supported;
  }
  deviation "/ni:network-instance/ni:instances/ni:instance/l3vpn:afs/l3vpn:af/bras-ipv4-address-manage:bas" {
    deviate not-supported;
  }
  deviation "/bras-cu-controller:bras-cu-controller/bras-ipv4-address-manage:ipv4-address-manage" {
    deviate not-supported;
  }

}
