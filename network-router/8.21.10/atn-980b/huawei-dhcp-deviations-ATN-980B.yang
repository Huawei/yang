/*
Copyright (C) 2021 Huawei Technologies Co., Ltd. All rights reserved.
*/
module huawei-dhcp-deviations-ATN-980B {
  namespace "urn:huawei:yang:huawei-dhcp-deviations-ATN-980B";
  prefix dhcp-devs-ATN-980B;

  import huawei-dhcp {
    prefix dhcp;
  }
  import huawei-ifm {
    prefix ifm;
  }
  import huawei-bd {
    prefix bd;
  }
  import huawei-vlan {
    prefix vlan;
  }

  organization
    "Huawei Technologies Co., Ltd.";
  contact
    "Huawei Industrial Base
     Bantian, Longgang
     Shenzhen 518129
     People's Republic of China
     Website: http://www.huawei.com
     Email: support@huawei.com";
  description
    "This module defines deviation statements for huawei-dhcp module.";

  revision 2021-05-07 {
    description
      "Initial revision.";
    reference "Huawei private.";
  }

  typedef dhcp-svr-sub-option-mode-deviations {
    type enumeration {
      enum ascii-mode {
        value 0;
        description
          "Ascii Mode.";
      }
      enum ip-mode {
        value 2;
        description
          "IP Mode.";
      }
    }
    description
      "Type of dhcp-svr-sub-option-mode.";
  }

  typedef ip-pool-address-reset-type-deviations {
    type enumeration {
      enum conflict {
        value 2;
        description
          "Conflict.";
      }
    }
    description
      "Type of ip-pool-address-reset.";
  }

  typedef option82-format-deviations {
    type enumeration {
      enum user-defined {
        value 3;
        description
          "DHCP option82 user-defined format.";
      }
      enum type1 {
        value 5;
        description
          "DHCP option82 type1 format.";
      }
      enum type2 {
        value 6;
        description
          "DHCP option82 type2 format.";
      }
      enum self-define {
        value 7;
        description
          "DHCP option82 self-define format.";
      }
      enum cn-telecom {
        value 9;
        description
          "DHCP option82 cn-telecom format.";
      }
      enum cn-telecom-inherit {
        value 12;
        description
          "DHCP option82 cn-telecom-inherit format.";
      }
    }
    description
      "Type of dhcp-opt82-format.";
  }

  deviation "/dhcp:dhcp/dhcp:relay/dhcp:global/dhcp:distribute-flag" {
    deviate not-supported;
  }
  deviation "/dhcp:dhcp/dhcp:server/dhcp:global-ip-pools/dhcp:global-ip-pool/dhcp:domain-lists" {
    deviate not-supported;
  }
  deviation "/dhcp:dhcp/dhcp:snooping/dhcp:white-lists" {
    deviate not-supported;
  }
  deviation "/bd:bd/bd:instances/bd:instance/dhcp:dhcp-snooping-bd/dhcp:basic-attribute/dhcp:nni-trust-enable" {
    deviate not-supported;
  }
  deviation "/dhcp:dhcp/dhcp:common/dhcp:global/dhcp:enable" {
    deviate replace {
      default "true";
    }
  }
  deviation "/dhcp:dhcp/dhcp:common/dhcp:session-car/dhcp:cir-value" {
    deviate replace {
      type uint32 {
        range "0..2000";
      }
    }
    deviate replace {
      default "110";
    }
    deviate replace {
      units "pps";
    }
  }
  deviation "/dhcp:dhcp/dhcp:common/dhcp:session-car/dhcp:cbs-value" {
    deviate replace {
      type uint32 {
        range "0..2000";
      }
    }
    deviate replace {
      default "110";
    }
    deviate replace {
      units "packet";
    }
  }
  deviation "/dhcp:dhcp/dhcp:common/dhcp:session-car/dhcp:pir-value" {
    deviate replace {
      type uint32 {
        range "0..2000";
      }
    }
    deviate replace {
      default "220";
    }
    deviate replace {
      units "pps";
    }
  }
  deviation "/dhcp:dhcp/dhcp:common/dhcp:session-car/dhcp:pbs-value" {
    deviate replace {
      type uint32 {
        range "0..2000";
      }
    }
    deviate replace {
      default "220";
    }
    deviate replace {
      units "packet";
    }
  }
  deviation "/dhcp:dhcp/dhcp:server/dhcp:global-ip-pools/dhcp:global-ip-pool/dhcp:ip-pool-name" {
    deviate replace {
      type string {
        length "1..32";
      }
    }
  }
  deviation "/dhcp:dhcp/dhcp:server/dhcp:global-ip-pools/dhcp:global-ip-pool/dhcp:domain-name" {
    deviate replace {
      type string {
        length "1..50";
      }
    }
  }
  deviation "/dhcp:dhcp/dhcp:server/dhcp:global-ip-pools/dhcp:global-ip-pool/dhcp:sections/dhcp:section/dhcp:section-index" {
    deviate replace {
      type uint32 {
        range "0..63";
      }
    }
  }
  deviation "/dhcp:dhcp/dhcp:server/dhcp:global-ip-pools/dhcp:global-ip-pool/dhcp:static-binds/dhcp:static-bind" {
    deviate replace {
      max-elements 64;
    }
  }
  deviation "/dhcp:dhcp/dhcp:server/dhcp:ip-pool-user-infos/dhcp:ip-pool-user-info/dhcp:pool-name" {
    deviate replace {
      type string {
        length "1..32";
      }
    }
  }
  deviation "/ifm:ifm/ifm:interfaces/ifm:interface/dhcp:dhcp-if/dhcp:option82-formats/dhcp:option82-format/dhcp:option82-format" {
    deviate replace {
      type dhcp-devs-ATN-980B:option82-format-deviations;
    }
  }
  deviation "/ifm:ifm/ifm:interfaces/ifm:interface/dhcp:dhcp-snooping-if/dhcp:basic-attribute/dhcp:max-user-number" {
    deviate replace {
      type uint32 {
        range "1..2048";
      }
    }
  }
  deviation "/vlan:vlan/vlan:vlans/vlan:vlan/dhcp:dhcp-vlan/dhcp:interface-option82-formats/dhcp:interface-option82-format/dhcp:option82-format" {
    deviate replace {
      type dhcp-devs-ATN-980B:option82-format-deviations;
    }
  }
  deviation "/vlan:vlan/vlan:vlans/vlan:vlan/dhcp:dhcp-snooping-vlan/dhcp:basic-attribute/dhcp:max-user-number" {
    deviate replace {
      type uint16 {
        range "1..2048";
      }
    }
  }
  deviation "/vlan:vlan/vlan:vlans/vlan:vlan/dhcp:dhcp-snooping-vlan/dhcp:vlan-interfaces/dhcp:vlan-interface/dhcp:max-user-number" {
    deviate replace {
      type uint32 {
        range "1..2048";
      }
    }
  }
  deviation "/bd:bd/bd:instances/bd:instance/dhcp:dhcp-snooping-bd/dhcp:basic-attribute/dhcp:max-user-number" {
    deviate replace {
      type uint32 {
        range "1..2048";
      }
    }
  }
}
