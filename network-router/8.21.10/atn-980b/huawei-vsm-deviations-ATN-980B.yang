/*
Copyright (C) 2021 Huawei Technologies Co., Ltd. All rights reserved.
*/
module huawei-vsm-deviations-ATN-980B {
  namespace "urn:huawei:yang:huawei-vsm-deviations-ATN-980B";
  prefix vsm-devs-ATN-980B;

  import huawei-vsm {
    prefix vsm;
  }

  organization
    "Huawei Technologies Co., Ltd.";

  contact
    "Huawei Industrial Base
     Bantian, Longgang
     Shenzhen 518129
     People's Republic of China
     Website: http://www.huawei.com
     Email: support@huawei.com";

  description
    "This module defines deviation statements for huawei-vsm module.";

  revision 2021-05-07 {
    description
      "Initial revision.";
    reference
      "Huawei private.";
  }

  deviation "/vsm:vsm/vsm:service-locations" {
    deviate not-supported;
  }
  deviation "/vsm:vsm/vsm:service-instance-groups" {
    deviate not-supported;
  }
  deviation "/vsm:vsm/vsm:monitor-location-groups" {
    deviate not-supported;
  }
  deviation "/vsm:vsm/vsm:on-board-mode" {
    deviate not-supported;
  }
  deviation "/vsm:vsm/vsm:ha" {
    deviate not-supported;
  }

}
