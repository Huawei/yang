/*
Copyright (C) 2021 Huawei Technologies Co., Ltd. All rights reserved.
*/
module huawei-pki-deviations-ATN-980B {
  namespace "urn:huawei:yang:huawei-pki-deviations-ATN-980B";
  prefix pki-devs-ATN-980B;

  import huawei-pki {
    prefix pki;
  }

  organization
    "Huawei Technologies Co., Ltd.";
  contact
    "Huawei Industrial Base
     Bantian, Longgang
     Shenzhen 518129
     People's Republic of China
     Website: http://www.huawei.com
     Email: support@huawei.com";
  description
    "This module defines deviation statements for huawei-pki module.";

  revision 2021-05-07 {
    description
      "Initial revision.";
    reference "Huawei private.";
  }

  deviation "/pki:certificate-import" {
    deviate not-supported;
  }
  deviation "/pki:certificate-delete" {
    deviate not-supported;
  }
}
