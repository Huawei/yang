/*
Copyright (C) 2021 Huawei Technologies Co., Ltd. All rights reserved.
*/
module huawei-ospfv3-deviations-ATN-980B {
  namespace "urn:huawei:yang:huawei-ospfv3-deviations-ATN-980B";
  prefix ospfv3-devs-ATN-980B;

  import huawei-ospfv3 {
    prefix ospfv3;
  }
  import huawei-ifm {
    prefix ifm;
  }
  import huawei-if-ip {
    prefix if-ip;
  }
  import huawei-ip {
    prefix ip;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-ospfv3 module.";

  revision 2021-05-07 {
    description
      "Initial revision.";
    reference "Huawei private.";
  }

  typedef import-rt-protocol-deviations {
    type enumeration {
      enum direct {
        value 1;
        description
          "Direct route.";
      }
      enum ospfv3 {
        value 7;
        description
          "OSPFv3 router.";
      }
      enum isis {
        value 3;
        description
          "ISIS protocol.";
      }
      enum static {
        value 4;
        description
          "Static route.";
      }
      enum ripng {
        value 8;
        description
          "RIPng routes.";
      }
      enum bgp {
        value 6;
        description
          "BGP protocol.";
      }
    }
    description
      "OSPFv3 import route protocol.";
  }

  deviation "/ospfv3:ospfv3/ospfv3:advertise-max-cost" {
    deviate not-supported;
  }
  deviation "/ospfv3:reset-redistribution" {
    deviate not-supported;
  }
  deviation "/ospfv3:reset-counter" {
    deviate not-supported;
  }
  deviation "/ospfv3:reset-process" {
    deviate not-supported;
  }
  deviation "/ospfv3:reset-peer" {
    deviate not-supported;
  }
  deviation "/ospfv3:reset-frr" {
    deviate not-supported;
  }
  deviation "/ni:network-instance/ni:instances/ni:instance/ospfv3:ospfv3/ospfv3:sites/ospfv3:site/ospfv3:import-routes/ospfv3:import-route/ospfv3:inherit-route-type" {
    deviate not-supported;
  }
  deviation "/ni:network-instance/ni:instances/ni:instance/ospfv3:ospfv3/ospfv3:sites/ospfv3:site/ospfv3:cost-bindings" {
    deviate not-supported;
  }
  deviation "/ospfv3:ospfv3/ospfv3:session-car/ospfv3:cir-interval" {
    deviate replace {
      default "1";
    }
    deviate replace {
      units "pps";
    }
  }
  deviation "/ospfv3:ospfv3/ospfv3:session-car/ospfv3:cbs-interval" {
    deviate replace {
      default "100";
    }
    deviate replace {
      units "pps";
    }
  }
  deviation "/ospfv3:ospfv3/ospfv3:session-car/ospfv3:pir-interval" {
    deviate replace {
      default "1500";
    }
    deviate replace {
      units "pps";
    }
  }
  deviation "/ospfv3:ospfv3/ospfv3:session-car/ospfv3:pbs-interval" {
    deviate replace {
      default "1500";
    }
    deviate replace {
      units "packet";
    }
  }
  deviation "/ospfv3:ospfv3/ospfv3:micro-isolation-car/ospfv3:cir" {
    deviate replace {
      default "1";
    }
    deviate replace {
      units "pps";
    }
  }
  deviation "/ospfv3:ospfv3/ospfv3:micro-isolation-car/ospfv3:cbs" {
    deviate replace {
      default "100";
    }
    deviate replace {
      units "packet";
    }
  }
  deviation "/ospfv3:ospfv3/ospfv3:micro-isolation-car/ospfv3:pir" {
    deviate replace {
      default "1500";
    }
    deviate replace {
      units "pps";
    }
  }
  deviation "/ospfv3:ospfv3/ospfv3:micro-isolation-car/ospfv3:pbs" {
    deviate replace {
      default "1500";
    }
    deviate replace {
      units "packet";
    }
  }
  deviation "/ni:network-instance/ni:instances/ni:instance/ospfv3:ospfv3/ospfv3:sites/ospfv3:site/ospfv3:nexthop-weights/ospfv3:nexthop-weight/ospfv3:if-name" {
    deviate delete {
      must '/ifm:ifm/ifm:interfaces/ifm:interface[ifm:name=current()]/ip:ipv6';
    }
    deviate add {
      must '/ifm:ifm/ifm:interfaces/ifm:interface[ifm:name=current()]/ip:ipv6 or /ni:network-instance/ni:instances/ni:instance/if-ip:ipv6-ifs/if-ip:ipv6-if[if-ip:name=current()/../ospfv3:if-name]';
    }
  }
  deviation "/ni:network-instance/ni:instances/ni:instance/ospfv3:ospfv3/ospfv3:sites/ospfv3:site/ospfv3:import-routes/ospfv3:import-route/ospfv3:protocol" {
    deviate replace {
      type ospfv3-devs-ATN-980B:import-rt-protocol-deviations;
    }
  }
  deviation "/ni:network-instance/ni:instances/ni:instance/ospfv3:ospfv3/ospfv3:sites/ospfv3:site/ospfv3:silent-interfaces/ospfv3:silent-interface/ospfv3:if-name" {
    deviate delete {
      must '/ifm:ifm/ifm:interfaces/ifm:interface[ifm:name=current()]/ip:ipv6';
    }
    deviate add {
      must '/ifm:ifm/ifm:interfaces/ifm:interface[ifm:name=current()]/ip:ipv6 or /ni:network-instance/ni:instances/ni:instance/if-ip:ipv6-ifs/if-ip:ipv6-if[if-ip:name=current()/../ospfv3:if-name]';
    }
  }
  deviation "/ni:network-instance/ni:instances/ni:instance/ospfv3:ospfv3/ospfv3:sites/ospfv3:site/ospfv3:undo-silent-interfaces/ospfv3:undo-silent-interface/ospfv3:if-name" {
    deviate delete {
      must '/ifm:ifm/ifm:interfaces/ifm:interface[ifm:name=current()]/ip:ipv6';
    }
    deviate add {
      must '/ifm:ifm/ifm:interfaces/ifm:interface[ifm:name=current()]/ip:ipv6 or /ni:network-instance/ni:instances/ni:instance/if-ip:ipv6-ifs/if-ip:ipv6-if[if-ip:name=current()/../ospfv3:if-name]';
    }
  }
  deviation "/ni:network-instance/ni:instances/ni:instance/ospfv3:ospfv3/ospfv3:sites/ospfv3:site/ospfv3:areas/ospfv3:area/ospfv3:interfaces/ospfv3:interface/ospfv3:name" {
    deviate delete {
      must '/ifm:ifm/ifm:interfaces/ifm:interface[ifm:name=current()]/ip:ipv6';
    }
    deviate add {
      must '/ifm:ifm/ifm:interfaces/ifm:interface[ifm:name=current()]/ip:ipv6 or /ni:network-instance/ni:instances/ni:instance/if-ip:ipv6-ifs/if-ip:ipv6-if[if-ip:name=current()/../ospfv3:name]';
    }
  }
}
