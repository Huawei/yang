/*
Copyright (C) 2019-2022 Huawei Technologies Co., Ltd. All rights reserved.
*/
module huawei-netconf {
  namespace "urn:huawei:yang:huawei-netconf";
  prefix netconf;
  import huawei-extension {
    prefix ext;
  }  
  organization
    "Huawei Technologies Co., Ltd.";
  contact
    "Huawei Industrial Base
     Bantian, Longgang
     Shenzhen 518129
     People's Republic of China
     Website: http://www.huawei.com
     Email: support@huawei.com";
  description
    "The NETCONF protocol defines a simple mechanism through which a network device can be managed, configuration data information can be retrieved, and new configuration data can be uploaded and manipulated.";
  revision 2022-01-05 {
    description
      "Add enable-alarms node.";
    reference
      "Huawei private.";
  }
  revision 2020-02-22 {
    description
      "Add rpc to manage active YANG modules.";
    reference
      "Huawei private.";
  }
  revision 2019-05-05 {
    description
      "Init revision.";
    reference
      "Huawei private.";
  }
  ext:task-name "netconf";  
  container netconf {
    description
      "The NETCONF protocol defines a simple mechanism through which a network device can be managed, configuration data information can be retrieved, and new configuration data can be uploaded and manipulated.";
    container operation-log-switch {
      description
        "Configure to get RPC operation log.";
      leaf get {
        type boolean;
        default "false";
        description
          "Enable/disable to get operation log.";
      }
    }

    container active-modules {
      config false;
      description
        "List of active YANG modules.";
      list active-module {
        key "module-name";
        config false;
        description
          "Statistics of active YANG module.";
        leaf module-name {
          type string {
            length "1..127";
          }
          description
            "Active YANG module name.";
        }
      }
    }
    container enable-alarms {
      description
        "List of NETCONF alarm.";
      list enable-alarm {
        key "alarm-name";
        description
          "Specify the enabled alarm.";
        leaf alarm-name {
          type enumeration {
            enum "connect-interrupt" {
              value 1;
              description
                "Specify connect-interrupt alarm.";
            }
          }
          description
            "Name of an enabled alarm.";
        }
      }
    }
  }
  rpc activate-module {
    description
      "Activate YANG modules.";
    input  {
      leaf module-name {
          type string {
            length "1..127";
          }
          mandatory true;
          description
            "The YANG module name to activate.";
      }
    }
  }
}
