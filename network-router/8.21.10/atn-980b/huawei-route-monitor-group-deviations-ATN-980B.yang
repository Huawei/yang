/*
Copyright (C) 2021 Huawei Technologies Co., Ltd. All rights reserved.
*/
module huawei-route-monitor-group-deviations-ATN-980B {
  namespace "urn:huawei:yang:huawei-route-monitor-group-deviations-ATN-980B";
  prefix rmg-devs-ATN-980B;

  import huawei-route-monitor-group {
    prefix rmg;
  }

  organization
    "Huawei Technologies Co., Ltd.";
  contact
    "Huawei Industrial Base
     Bantian, Longgang
     Shenzhen 518129
     People's Republic of China
     Website: http://www.huawei.com
     Email: support@huawei.com";
  description
    "This module defines deviation statements for huawei-route-monitor-group module.";

  revision 2021-05-07 {
    description
      "Initial revision.";
    reference "Huawei private.";
  }

  deviation "/rmg:route-monitor-group/rmg:monitor-groups/rmg:monitor-group/rmg:operator-and" {
    deviate not-supported;
  }
  deviation "/rmg:route-monitor-group/rmg:monitor-groups/rmg:monitor-group/rmg:trigger-down-delay" {
    deviate not-supported;
  }
}
