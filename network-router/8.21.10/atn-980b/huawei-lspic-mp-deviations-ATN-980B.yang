/*
Copyright (C) 2019 Huawei Technologies Co., Ltd. All rights reserved.
*/
module huawei-lspic-mp-deviations-ATN-980B {
  namespace "urn:huawei:yang:huawei-lspic-mp-deviations-ATN-980B";
  prefix "lspic-mp-devs-ATN-980B";

  import huawei-ifm {
    prefix ifm;
  }
  import huawei-ppp-net {
    prefix ppp-net;
  }
  import huawei-lspic-mp {
    prefix lspic-mp;
  }
  organization
    "Huawei Technologies Co., Ltd.";
  contact
    "Huawei Industrial Base
     Bantian, Longgang
     Shenzhen 518129
     People's Republic of China
     Website: http://www.huawei.com
     Email: support@huawei.com";
  description
    "MP-group deviations.";
  revision 2019-05-05 {
    description
      "Init revision.";
    reference
      "Huawei private.";
  }
  deviation /ifm:ifm/ifm:interfaces/ifm:interface/ppp-net:ppp-net/ppp-net:multilink-ppp/ppp-net:mp-base/lspic-mp:qos-attribute/lspic-mp:dynamic-bandwidth-enable {
    deviate not-supported;
  }
  deviation /ifm:ifm/ifm:interfaces/ifm:interface/ppp-net:ppp-net/ppp-net:multilink-ppp/ppp-net:mp-base/lspic-mp:qos-attribute/lspic-mp:low-latency-enable {
    deviate not-supported;
  }
  deviation /ifm:ifm/ifm:interfaces/ifm:interface/ppp-net:ppp-net/ppp-net:multilink-ppp/ppp-net:mp-base/lspic-mp:qos-attribute/lspic-mp:packet-priority {
    deviate not-supported;
  }
  deviation /ifm:ifm/ifm:interfaces/ifm:interface/ppp-net:ppp-net/ppp-net:multilink-ppp/ppp-net:mp-base/lspic-mp:qos-attribute/lspic-mp:packet-queue-depth {
    deviate not-supported;
  }
}
