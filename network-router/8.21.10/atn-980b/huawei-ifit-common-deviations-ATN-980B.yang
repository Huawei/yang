/*
Copyright (C) 2021 Huawei Technologies Co., Ltd. All rights reserved.
*/
module huawei-ifit-common-deviations-ATN-980B {
  namespace "urn:huawei:yang:huawei-ifit-common-deviations-ATN-980B";
  prefix ifit-common-devs-ATN-980B;

  import huawei-ifit-common {
    prefix ifit-common;
  }
  import huawei-extension {
    prefix ext;
  }
  import huawei-ifm {
    prefix ifm;
  }
  import huawei-ifit {
    prefix ifit;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-ifit-common module.";

  revision 2021-05-07 {
    description
      "Initial revision.";
    reference "Huawei private.";
  }

  deviation "/ifit:ifit/ifit-common:ifit-common/ifit-common:global/ifit-common:clock-mode" {
    deviate not-supported;
  }
  deviation "/ifit:ifit/ifit-common:ifit-common/ifit-common:whitelist-groups/ifit-common:whitelist-group/ifit-common:mode" {
    deviate not-supported;
  }
  deviation "/ifit:ifit/ifit-common:ifit-common/ifit-common:whitelist-groups/ifit-common:whitelist-group/ifit-common:whitelist-rules/ifit-common:whitelist-rule/ifit-common:source-port-end" {
    deviate not-supported;
  }
  deviation "/ifit:ifit/ifit-common:ifit-common/ifit-common:whitelist-groups/ifit-common:whitelist-group/ifit-common:whitelist-rules/ifit-common:whitelist-rule/ifit-common:destination-port-end" {
    deviate not-supported;
  }
  deviation "/ifit:ifit/ifit-common:ifit-common/ifit-common:native-ip-learning" {
    deviate not-supported;
  }
  deviation "/ni:network-instance/ni:instances/ni:instance/ifit-common:ifit-learning/ifit-common:per-packet-delay-measure" {
    deviate not-supported;
  }
  deviation "/ifm:ifm/ifm:interfaces/ifm:interface/ifit-common:ifit" {
    deviate not-supported;
  }
  deviation "/ifit:ifit/ifit-common:ifit-common/ifit-common:static-instances/ifit-common:static-instance" {
    deviate delete {
      must "../../global/clock-mode='common' or (disorder-measure-enable='false' and gtpu-sn-measure-enable='false')";
    }
  }
  deviation "/ifit:ifit/ifit-common:ifit-common/ifit-common:static-instances/ifit-common:static-instance/ifit-common:flow" {
    deviate delete {
      must "../../../global/clock-mode!='precision-full' or ../interval=10";
    }
    deviate delete {
      must "../../../global/clock-mode='common' or (not(address-type) and not(peer-evpl-id) and not(peer-ip) and not(peer-locator-prefix))";
    }
  }
  deviation "/ifit:ifit/ifit-common:ifit-common/ifit-common:static-instances/ifit-common:static-instance/ifit-common:flow/ifit-common:flow-type" {
    deviate delete {
      must "../../../../global/clock-mode='common' or ../flow-type='unidirection'";
    }
  }
  deviation "/ifit:ifit/ifit-common:ifit-common/ifit-common:whitelist-groups/ifit-common:whitelist-group/ifit-common:whitelist-rules/ifit-common:whitelist-rule/ifit-common:address-type/ifit-common:ipv6-condition/ifit-common:source-ipv6-mask" {
    deviate replace {
      type uint8 {
        range "32..96";
      }
    }
  }
  deviation "/ifit:ifit/ifit-common:ifit-common/ifit-common:whitelist-groups/ifit-common:whitelist-group/ifit-common:whitelist-rules/ifit-common:whitelist-rule/ifit-common:address-type/ifit-common:ipv6-condition/ifit-common:destination-ipv6-mask" {
    deviate replace {
      type uint8 {
        range "32..128";
      }
    }
  }
  deviation "/ni:network-instance/ni:instances/ni:instance/ifit-common:ifit-learning" {
    deviate delete {
      must "/ifit:ifit/ifit-common:ifit-common/ifit-common:global/ifit-common:clock-mode='common'";
    }
  }
  ext:deviation-ext "/ifit:ifit/ifit-common:ifit-common/ifit-common:whitelist-groups/ifit-common:whitelist-group/ifit-common:whitelist-rules/ifit-common:whitelist-rule/ifit-common:address-type/ifit-common:ipv6-condition/ifit-common:source-ipv6-mask" {
    ext:deviate-ext "replace" {
      ext:dynamic-default {
        ext:default-value "96" {
          when '../source-ipv6-address';
        }
      }
    }
  }
}
