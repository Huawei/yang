/******************************************************
 * Copyright (C) 2021 Huawei Technologies Co., Ltd. All rights reserved.
 ***************************************************/
module huawei-pki {
  yang-version 1;
  namespace "urn:huawei:yang:huawei-pki";
  prefix pki;
  import huawei-extension {
    prefix ext;
  }
  import huawei-pub-type {
    prefix pub-type;
  }
  organization
    "Huawei Technologies Co., Ltd.";
  contact
    "Huawei Industrial Base
    Bantian, Longgang
    Shenzhen 518129
    People's Republic of China
    Website: http://www.huawei.com
    Email: support@huawei.com";
  description
    "This module contains a collection of YANG definitions for configuring PKI certificate operation.";
  revision 2021-06-02 {
    description
      "Roll back poc test version modification.";
    reference
      "Huawei private.";
  }
  revision 2021-04-08 {
    description
      "Add node of CMPv2 configuration.";
    reference
      "Huawei private.";
  }
  revision 2021-01-06 {
    description
      "Initial revision.";
    reference
      "Huawei private.";
  }
  typedef certificate-type {
    type enumeration {
      enum "ca" {
        value 0;
        description
          "Certificate awarded by a CA.";
      }
      enum "local" {
        value 1;
        description
          "Local stored certifacation.";
      }
      enum "default-ca" {
        value 2;
        description
          "Default CA certificate.";
      }
      enum "default-local" {
        value 3;
        description
          "Default local certificate.";
      }
      enum "crl" {
        value 4;
        description
          "CRL certificate.";
      }
      enum "ocsp" {
        value 5;
        description
          "OCSP certificate.";
      }
    }
    description
      "Certificate type.";
  }
  typedef certificate-file-format {
    type enumeration {
      enum "pem" {
        value 0;
        description
          "PEM format.";
      }
      enum "der" {
        value 1;
        description
          "DER format.";
      }
      enum "pkcs12" {
        value 2;
        description
          "PKCS12 format.";
      }
    }
    description
      "Certificate file format.";
  }
  rpc certificate-import {
    description
      "Certificate import operation.";
    input  {
      container certificates {
        description
          "List of certificate import operation.";
        list certificate {
          key "name type";
          description
            "Import certificates.";
          leaf name {
            type string {
              length "1..64";
            }
            description
              "Certificate file name.";
          }
          leaf type {
            type certificate-type;
            description
              "Certificate type.";
          }
          leaf domain-name {
            type string {
              length "1..64";
            }
            description
              "PKI domain name.";
          }
          leaf format {
            type certificate-file-format;
            description
              "Certificate file format.";
          }
          leaf password {
            when "(../type = 'local') and (../format = 'pkcs12')";
            type pub-type:password {
              length "1..32";
            }
            mandatory true;
            description
              "Local key-pair encryption password.";
          }
        }
      }
    }
  }
  rpc certificate-delete {
    description
      "Certificate delete operation.";
    input  {
      container certificates {
        description
          "List of certificate delete operation.";
        list certificate {
          key "name type";
          description
            "Delete certificates.";
          leaf name {
            type string {
              length "1..64";
            }
            description
              "Certificate file name.";
          }
          leaf type {
            type certificate-type;
            description
              "Certificate type.";
          }
        }
      }
    }
  }
  rpc certificate-replace {
    description
      "Certificate replace operation.";
    input {
      container certificates {
        description
          "List of certificate replace operation.";
        list certificate {
          key "file-name type domain-name";
          description "Certificates to replace.";
          
          leaf file-name {
            type string {
              length "1..64";
            }
            description
              "Certificate file name.";
          }

          leaf type {
            type certificate-type;
            description
              "Certificate type.";
          }
          leaf domain-name {
            type string {
              length "1..64";
            }
            description
              "Pki domain name.";
          }
          leaf password {
            type pub-type:password {
              length "1..32";
            }
            description
              "Local key-pair encryption password.";
          }
        }
      }
    }
  }
  ext:task-name "pki";
}
