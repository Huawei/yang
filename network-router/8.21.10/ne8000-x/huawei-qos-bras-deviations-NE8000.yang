/*
Copyright (C) 2021 Huawei Technologies Co., Ltd. All rights reserved.
*/
module huawei-qos-bras-deviations-NE8000 {
  namespace "urn:huawei:yang:huawei-qos-bras-deviations-NE8000";
  prefix qos-bras-devs-NE8000;

  import huawei-qos-bras {
    prefix qos-bras;
  }

  import huawei-aaa {
    prefix aaa;
  }

  import huawei-bras-qos {
    prefix bras-qos;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-qos-bras module.";

  revision 2021-05-07 {
    description
      "Initial revision.";
    reference
      "Huawei private.";
  }

  deviation "/aaa:aaa/aaa:domains/aaa:domain/bras-basic-access:bas/bras-qos:bras-qos/qos-bras:l2-user-priority" {
    deviate not-supported;
  }

}
