/*
Copyright (C) 2021 Huawei Technologies Co., Ltd. All rights reserved.
*/
module huawei-openconfig-lacp-deviations-NE8000 {
  namespace "urn:huawei:yang:huawei-openconfig-lacp-deviations-NE8000";
  prefix oc-lacp-devs-NE8000;

  import openconfig-lacp {
    prefix oc-lacp;
  }

  organization
    "Huawei Technologies Co., Ltd.";
  contact
    "Huawei Industrial Base
     Bantian, Longgang
     Shenzhen 518129
     People's Republic of China
     Website: http://www.huawei.com
     Email: support@huawei.com";
  description
    "This module defines deviation statements for openconfig-lacp module.";

  revision 2021-05-07 {
    description
      "Initial revision.";
    reference "Huawei private.";
  }

  typedef lacp-activity-type-deviations {
    type enumeration {
      enum ACTIVE {
        value 1;
        description
          "Interface is an active member, i.e., will detect and maintain aggregates.";
      }
    }
    description
      "Describes the LACP membership type, active or passive, of the interface in the aggregate.";
    reference "IEEE 802.1AX-2008";
  }

  deviation "/oc-lacp:lacp/oc-lacp:config" {
    deviate not-supported;
  }
  deviation "/oc-lacp:lacp/oc-lacp:state" {
    deviate not-supported;
  }
  deviation "/oc-lacp:lacp/oc-lacp:interfaces/oc-lacp:interface/oc-lacp:config/oc-lacp:system-id-mac" {
    deviate not-supported;
  }
  deviation "/oc-lacp:lacp/oc-lacp:interfaces/oc-lacp:interface/oc-lacp:state" {
    deviate not-supported;
  }
  deviation "/oc-lacp:lacp/oc-lacp:interfaces/oc-lacp:interface/oc-lacp:members" {
    deviate not-supported;
  }
  deviation "/oc-lacp:lacp/oc-lacp:interfaces/oc-lacp:interface/oc-lacp:config/oc-lacp:lacp-mode" {
    deviate replace {
      type oc-lacp-devs-NE8000:lacp-activity-type-deviations;
    }
  }
}
