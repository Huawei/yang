/*
Copyright (C) 2021 Huawei Technologies Co., Ltd. All rights reserved.
*/
module huawei-bras-vas-deviations-NE8000 {
  namespace "urn:huawei:yang:huawei-bras-vas-deviations-NE8000";
  prefix bras-vas-devs-NE8000;

  import huawei-bras-vas {
    prefix bras-vas;
  }

  import huawei-devm {
    prefix devm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-vas module.";

  revision 2021-05-07 {
    description
      "Initial revision.";
    reference
      "Huawei private.";
  }

  deviation "/bras-vas:bras-vas/bras-vas:vas-policys/bras-vas:vas-policy/bras-vas:user-group-bind-nats" {
    deviate not-supported;
  }
  deviation "/devm:devm/devm:mpu-boards/devm:mpu-board/bras-basic-access:bras/bras-vas:vas" {
    deviate not-supported;
  }

}
