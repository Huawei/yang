/*
Copyright (C) 2021 Huawei Technologies Co., Ltd. All rights reserved.
*/
module huawei-cfg-notification-deviations-NE8000 {
  namespace "urn:huawei:yang:huawei-cfg-notification-deviations-NE8000";
  prefix cfg-notification-devs-NE8000;

  import huawei-cfg-notification {
    prefix cfg-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-cfg-notification module.";

  revision 2021-05-07 {
    description
      "Initial revision.";
    reference "Huawei private.";
  }

  deviation "/cfg-notification:configuration-lock" {
    deviate not-supported;
  }
  deviation "/cfg-notification:configuration-unlock" {
    deviate not-supported;
  }
  deviation "/cfg-notification:running-config-change" {
    deviate not-supported;
  }
}
