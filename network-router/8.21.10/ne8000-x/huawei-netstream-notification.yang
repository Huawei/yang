/*
Copyright (C) 2020 Huawei Technologies Co., Ltd. All rights reserved.
*/
module huawei-netstream-notification {
  yang-version 1;
  namespace "urn:huawei:yang:huawei-netstream-notification";
  prefix netstream-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of netstream.";
  revision 2020-09-01 {
    description
      "Initial revision.";
    reference
      "Huawei private.";
  }
  ext:task-name "netstream";
  notification sampler-rate-inconsistent {
    description
      "The configured NetStream sampling ratio was different from the effective one.";
    leaf slot-id {
      type string {
        length "1..31";
      }
      description
        "Slot Id.";
    }
    leaf fix-packets-lower-limit {
      type string {
        length "1..31";
      }
      description
        "Lower limit for fixed-packet-number-based sampling ratio.";
    }
    leaf random-packets-lower-limit {
      type string {
        length "1..31";
      }
      description
        "Lower limit for random-packet-number-based sampling ratio.";
    }
    leaf fix-time-lower-limit {
      type string {
        length "1..31";
      }
      description
        "Lower limit for fixed-time-based sampling ratio.";
    }
  }
  notification sampler-rate-inconsistent-resume {
    description
      "The configured NetStream sampling ratio was same from the effective one.";
    leaf slot-id {
      type string {
        length "1..31";
      }
      description
        "Slot Id.";
    }
    leaf fix-packets-lower-limit {
      type string {
        length "1..31";
      }
      description
        "Lower limit for fixed-packet-number-based sampling ratio.";
    }
    leaf random-packets-lower-limit {
      type string {
        length "1..31";
      }
      description
        "Lower limit for random-packet-number-based sampling ratio.";
    }
    leaf fix-time-lower-limit {
      type string {
        length "1..31";
      }
      description
        "Lower limit for fixed-time-based sampling ratio.";
    }
  }
}
