/*
Copyright (C) 2021 Huawei Technologies Co., Ltd. All rights reserved.
*/
module huawei-bras-cu-controller-deviations-NE8000 {
  namespace "urn:huawei:yang:huawei-bras-cu-controller-deviations-NE8000";
  prefix bras-cu-controller-devs-NE8000;

  import huawei-bras-cu-controller {
    prefix bras-cu-controller;
  }

  import huawei-devm-vnf {
    prefix devm-vnf;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-cu-controller module.";

  revision 2021-05-07 {
    description
      "Initial revision.";
    reference
      "Huawei private.";
  }

  deviation "/bras-cu-controller:bras-cu-controller" {
    deviate not-supported;
  }
  deviation "/bras-cu-controller:reset-south-conflict-by-up" {
    deviate not-supported;
  }
  deviation "/bras-cu-controller:reset-south-conflict-all-up" {
    deviate not-supported;
  }
  deviation "/devm-vnf:devm-vnf/devm-vnf:vnf-boards/devm-vnf:vnf-board/bras-cu-controller:cp-cpu-defend" {
    deviate not-supported;
  }

}
