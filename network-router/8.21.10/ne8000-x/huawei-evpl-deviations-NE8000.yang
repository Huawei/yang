/*
Copyright (C) 2021 Huawei Technologies Co., Ltd. All rights reserved.
*/
module huawei-evpl-deviations-NE8000 {
  namespace "urn:huawei:yang:huawei-evpl-deviations-NE8000";
  prefix evpl-devs-NE8000;

  import huawei-evpl {
    prefix evpl;
  }

  organization
    "Huawei Technologies Co., Ltd.";
  contact
    "Huawei Industrial Base
     Bantian, Longgang
     Shenzhen 518129
     People's Republic of China
     Website: http://www.huawei.com
     Email: support@huawei.com";
  description
    "This module defines deviation statements for huawei-evpl module.";

  revision 2021-05-07 {
    description
      "Initial revision.";
    reference "Huawei private.";
  }

  deviation "/evpl:evpl/evpl:instances/evpl:instance/evpl:evpl-statistics" {
    deviate not-supported;
  }
}
