/*
Copyright (C) 2021 Huawei Technologies Co., Ltd. All rights reserved.
*/
module huawei-vsm-deviations-NE8000 {
  namespace "urn:huawei:yang:huawei-vsm-deviations-NE8000";
  prefix vsm-devs-NE8000;

  import huawei-vsm {
    prefix vsm;
  }

  organization
    "Huawei Technologies Co., Ltd.";

  contact
    "Huawei Industrial Base
     Bantian, Longgang
     Shenzhen 518129
     People's Republic of China
     Website: http://www.huawei.com
     Email: support@huawei.com";

  description
    "This module defines deviation statements for huawei-vsm module.";

  revision 2021-05-07 {
    description
      "Initial revision.";
    reference
      "Huawei private.";
  }

  deviation "/vsm:vsm/vsm:service-instance-groups/vsm:service-instance-group/vsm:remote-backup-service" {
    deviate not-supported;
  }
  deviation "/vsm:vsm/vsm:service-instance-groups/vsm:service-instance-group/vsm:binded-service-locations/vsm:binded-service-location/vsm:weight" {
    deviate not-supported;
  }
  deviation "/vsm:vsm/vsm:monitor-location-groups" {
    deviate not-supported;
  }
  deviation "/vsm:vsm/vsm:on-board-mode" {
    deviate not-supported;
  }
  deviation "/vsm:vsm/vsm:ha" {
    deviate not-supported;
  }

}
