/*
Copyright (C) 2021 Huawei Technologies Co., Ltd. All rights reserved.
*/
module huawei-bras-https-redirect-deviations-NE8000 {
  namespace "urn:huawei:yang:huawei-bras-https-redirect-deviations-NE8000";
  prefix bras-https-redirect-devs-NE8000;

  import huawei-bras-https-redirect {
    prefix bras-https-redirect;
  }

  import huawei-devm {
    prefix devm;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-https-redirect module.";

  revision 2021-05-07 {
    description
      "Initial revision.";
    reference
      "Huawei private.";
  }

  deviation "/devm:devm/devm:mpu-boards/devm:mpu-board/bras-https-redirect:https-redirect" {
    deviate not-supported;
  }

}
