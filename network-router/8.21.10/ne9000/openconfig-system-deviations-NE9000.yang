module openconfig-system-deviations-NE9000 {
  yang-version 1;
  namespace "urn:huawei:yang:openconfig-system-deviations-NE9000";
  prefix of-sys-devs-NE9000;

  import openconfig-system {
    prefix oc-sys;
  }

  organization
    "Huawei Technologies Co.,Ltd.";
  contact
    "Huawei Industrial Base Bantian, Longgang Shenzhen 518129
        People's Republic of China
        Website: http://www.huawei.com Email: support@huawei.com";
  description
    "Model for managing system-wide services and functions on
     network devices.

     Portions of this code were derived from IETF RFC 7317.
     Please reproduce this note if possible.

     IETF code is subject to the following copyright and license:
     Copyright (c) IETF Trust and the persons identified as authors of
     the code.
     All rights reserved.

     Redistribution and use in source and binary forms, with or without
     modification, is permitted pursuant to, and subject to the license
     terms contained in, the Simplified BSD License set forth in
     Section 4.c of the IETF Trust's Legal Provisions Relating
     to IETF Documents (http://trustee.ietf.org/license-info).";

  revision 2018-04-20;

  deviation "/oc-sys:system/oc-sys:config" {
    deviate not-supported;
  }
  deviation "/oc-sys:system/oc-sys:state" {
    deviate not-supported;
  }
  deviation "/oc-sys:system/oc-sys:clock" {
    deviate not-supported;
  }
  deviation "/oc-sys:system/oc-sys:dns/oc-sys:servers/oc-sys:server/oc-sys:config/oc-sys:port" {
    deviate not-supported;
  }
  deviation "/oc-sys:system/oc-sys:dns/oc-sys:servers/oc-sys:server/oc-sys:state/oc-sys:port" {
    deviate not-supported;
  }
  deviation "/oc-sys:system/oc-sys:dns/oc-sys:host-entries/oc-sys:host-entry/oc-sys:config/oc-sys:alias" {
    deviate not-supported;
  }
  deviation "/oc-sys:system/oc-sys:dns/oc-sys:host-entries/oc-sys:host-entry/oc-sys:state/oc-sys:alias" {
    deviate not-supported;
  }
  deviation "/oc-sys:system/oc-sys:dns/oc-sys:host-entries/oc-sys:host-entry/oc-sys:config/oc-sys:hostname" {
    deviate replace {
      type string {
        length "1..255";
      }
    }
  }
  deviation "/oc-sys:system/oc-sys:dns/oc-sys:host-entries/oc-sys:host-entry/oc-sys:state/oc-sys:hostname" {
    deviate replace {
      type string {
        length "1..255";
      }
    }
  }
  deviation "/oc-sys:system/oc-sys:dns/oc-sys:host-entries/oc-sys:host-entry" {
    deviate add {
      must '(count(/oc-sys:system/oc-sys:dns/oc-sys:host-entries/oc-sys:host-entry) > 0 and ((/oc-sys:system/oc-sys:dns/oc-sys:host-entries/oc-sys:host-entry/oc-sys:config/oc-sys:ipv4-address) or (/oc-sys:system/oc-sys:dns/oc-sys:host-entries/oc-sys:host-entry/oc-sys:config/oc-sys:ipv6-address))) or (count(/oc-sys:system/oc-sys:dns/oc-sys:host-entries/oc-sys:host-entry) = 0)';
    }
  }
  deviation "/oc-sys:system/oc-sys:ntp" {
    deviate not-supported;
  }
  deviation "/oc-sys:system/oc-sys:ssh-server" {
    deviate not-supported;
  }
  deviation "/oc-sys:system/oc-sys:telnet-server" {
    deviate not-supported;
  }
  deviation "/oc-sys:system/oc-sys:logging" {
    deviate not-supported;
  }
  deviation "/oc-sys:system/oc-sys:aaa" {
    deviate not-supported;
  }
  deviation "/oc-sys:system/oc-sys:memory" {
    deviate not-supported;
  }
  deviation "/oc-sys:system/oc-sys:cpus" {
    deviate not-supported;
  }
  deviation "/oc-sys:system/oc-sys:processes" {
    deviate not-supported;
  }
  deviation "/oc-sys:system/oc-sys:alarms" {
    deviate not-supported;
  }
}
