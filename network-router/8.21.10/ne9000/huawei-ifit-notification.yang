/*
Copyright (C) 2021 Huawei Technologies Co., Ltd. All rights reserved.
*/
module huawei-ifit-notification {
  yang-version 1;
  namespace "urn:huawei:yang:huawei-ifit-notification";
  prefix ifit-notification;
  import huawei-extension {
    prefix ext;
  } 
  organization
    "Huawei Technologies Co., Ltd.";
  contact
    "Huawei Industrial Base
    Bantian, Longgang
    Shenzhen 518129
    People's Republic of China
    Website: http://www.huawei.com
    Email: support@huawei.com";
  description
    "Notification of ifit.";

  revision 2021-02-01 {
    description
      "Initial revision.";
    reference
      "Huawei private.";
  }

  ext:task-name  "ifit";

  notification dynflow-ingress-exceed {
    description
      "The number of IFIT dynamic ingress flow reaches the upper limit.";
    leaf upper-limit {
      type uint32;
      description
        "Total dynamic ingress flow number upper limit of IFIT.";
    }
  }
  notification dynflow-ingress-resume {
    description
      "The number of IFIT dynamic ingress flow is below the upper limit.";
    leaf upper-limit {
      type uint32;
      description
        "Total dynamic ingress flow number upper limit of IFIT.";
    }
  }
  notification dynflow-midegress-exceed {
    description
      "The number of IFIT dynamic midegress flow reaches the upper limit.";
    leaf upper-limit {
      type uint32;
      description
        "Total dynamic midegress flow number upper limit of IFIT.";
    }
  }
  notification dynflow-midegress-resume {
    description
      "The number of IFIT dynamic midegress flow is below the upper limit.";
    leaf upper-limit {
      type uint32;
      description
        "Total dynamic midegress flow number upper limit of IFIT.";
    }
  }
  notification ingress-exceed {
    description
      "The number of IFIT ingress flow reaches the upper limit.";
    leaf upper-limit {
      type uint32;
      description
        "Total ingress flow number upper limit of IFIT.";
    }
  }
  notification ingress-resume {
    description
      "The number of IFIT ingress flow is below the upper limit.";
    leaf upper-limit {
      type uint32;
      description
        "Total ingress flow number upper limit of IFIT.";
    }
  }
  notification measurement-flow-exceed {
    description
      "The number of IFIT measurement flow reaches the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
  notification measurement-flow-resume {
    description
      "The number of IFIT measurement flow is below the upper limit.";
    leaf node-type {
      type string {
        length "1..64";
      }
      description
        "The measurement flow node type of IFIT.";
    }
    leaf flow-type {
      type string {
        length "1..64";
      }
      description
        "The measurement flow type of IFIT.";
    }
    leaf upper-limit {
      type uint32;
      description
        "Total measurement flow number upper limit of IFIT.";
    }
  }
}
