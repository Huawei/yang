/*
Copyright (C) 2021 Huawei Technologies Co., Ltd. All rights reserved.
*/
module huawei-pic-notification-deviations-NE9000 {
  namespace "urn:huawei:yang:huawei-pic-notification-deviations-NE9000";
  prefix pic-notification-devs-NE9000;

  import huawei-pic-notification {
    prefix pic-notification;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic-notification module.";

  revision 2021-05-07 {
    description
      "Initial revision.";
    reference
      "Huawei private.";
  }

  deviation "/pic-notification:optical-unauthorized" {
    deviate not-supported;
  }
  deviation "/pic-notification:optical-unauthorized-resume" {
    deviate not-supported;
  }
  deviation "/pic-notification:optical-invalid" {
    deviate not-supported;
  }
  deviation "/pic-notification:optical-invalid-resume" {
    deviate not-supported;
  }
  deviation "/pic-notification:flow-control-pause-frame-abnormal" {
    deviate not-supported;
  }
  deviation "/pic-notification:flow-control-pause-frame-abnormal-resume" {
    deviate not-supported;
  }
  deviation "/pic-notification:au-hp" {
    deviate not-supported;
  }
  deviation "/pic-notification:au-hp-resume" {
    deviate not-supported;
  }
  deviation "/pic-notification:b1-default-exceed" {
    deviate not-supported;
  }
  deviation "/pic-notification:b1-default-exceed-resume" {
    deviate not-supported;
  }
  deviation "/pic-notification:bip2-default-exceed" {
    deviate not-supported;
  }
  deviation "/pic-notification:bip2-default-exceed-resume" {
    deviate not-supported;
  }
  deviation "/pic-notification:b3-default-exceed" {
    deviate not-supported;
  }
  deviation "/pic-notification:b3-default-exceed-resume" {
    deviate not-supported;
  }
  deviation "/pic-notification:channel-loopback" {
    deviate not-supported;
  }
  deviation "/pic-notification:channel-loopback-resume" {
    deviate not-supported;
  }
  deviation "/pic-notification:cpos-e1-rai-signal" {
    deviate not-supported;
  }
  deviation "/pic-notification:cpos-e1-rai-signal-resume" {
    deviate not-supported;
  }
  deviation "/pic-notification:downstream-e1-cpos" {
    deviate not-supported;
  }
  deviation "/pic-notification:downstream-e1-cpos-resume" {
    deviate not-supported;
  }
  deviation "/pic-notification:loss-of-frame-e1-cpos" {
    deviate not-supported;
  }
  deviation "/pic-notification:loss-of-frame-e1-cpos-resume" {
    deviate not-supported;
  }
  deviation "/pic-notification:loss-multiframe-e1-cpos" {
    deviate not-supported;
  }
  deviation "/pic-notification:loss-multiframe-e1-cpos-resume" {
    deviate not-supported;
  }
  deviation "/pic-notification:upstream-e1-cpos" {
    deviate not-supported;
  }
  deviation "/pic-notification:upstream-e1-cpos-resume" {
    deviate not-supported;
  }
  deviation "/pic-notification:remote-indication-e1" {
    deviate not-supported;
  }
  deviation "/pic-notification:remote-indication-e1-resume" {
    deviate not-supported;
  }
  deviation "/pic-notification:downstream-e1" {
    deviate not-supported;
  }
  deviation "/pic-notification:downstream-e1-resume" {
    deviate not-supported;
  }
  deviation "/pic-notification:errored-second-exceed" {
    deviate not-supported;
  }
  deviation "/pic-notification:errored-second-exceed-resume" {
    deviate not-supported;
  }
  deviation "/pic-notification:loss-multiframe-e1" {
    deviate not-supported;
  }
  deviation "/pic-notification:loss-multiframe-e1-resume" {
    deviate not-supported;
  }
  deviation "/pic-notification:upstream-e1" {
    deviate not-supported;
  }
  deviation "/pic-notification:upstream-e1-resume" {
    deviate not-supported;
  }
  deviation "/pic-notification:remote-e3" {
    deviate not-supported;
  }
  deviation "/pic-notification:remote-e3-resume" {
    deviate not-supported;
  }
  deviation "/pic-notification:upstream-e3" {
    deviate not-supported;
  }
  deviation "/pic-notification:upstream-e3-resume" {
    deviate not-supported;
  }
  deviation "/pic-notification:j0-trace-mismatch" {
    deviate not-supported;
  }
  deviation "/pic-notification:j0-trace-mismatch-resume" {
    deviate not-supported;
  }
  deviation "/pic-notification:signal-mismatch-lp" {
    deviate not-supported;
  }
  deviation "/pic-notification:signal-mismatch-lp-resume" {
    deviate not-supported;
  }
  deviation "/pic-notification:trace-mismatch-lp" {
    deviate not-supported;
  }
  deviation "/pic-notification:trace-mismatch-lp-resume" {
    deviate not-supported;
  }
  deviation "/pic-notification:unequipped-lp" {
    deviate not-supported;
  }
  deviation "/pic-notification:unequipped-lp-resume" {
    deviate not-supported;
  }
  deviation "/pic-notification:out-of-lock-clock" {
    deviate not-supported;
  }
  deviation "/pic-notification:out-of-lock-clock-resume" {
    deviate not-supported;
  }
  deviation "/pic-notification:tributary-unit-lp" {
    deviate not-supported;
  }
  deviation "/pic-notification:tributary-unit-lp-resume" {
    deviate not-supported;
  }
  deviation "/pic-notification:v5-virtual-container" {
    deviate not-supported;
  }
  deviation "/pic-notification:v5-virtual-container-resume" {
    deviate not-supported;
  }
  deviation "/pic-notification:loss-au-lp" {
    deviate not-supported;
  }
  deviation "/pic-notification:loss-au-lp-resume" {
    deviate not-supported;
  }
  deviation "/pic-notification:remote-defect-lp" {
    deviate not-supported;
  }
  deviation "/pic-notification:remote-defect-lp-resume" {
    deviate not-supported;
  }
  deviation "/pic-notification:remote-failure-lp" {
    deviate not-supported;
  }
  deviation "/pic-notification:remote-failure-lp-resume" {
    deviate not-supported;
  }
  deviation "/pic-notification:resource-dead-line" {
    deviate not-supported;
  }
  deviation "/pic-notification:resource-dead-line-resume" {
    deviate not-supported;
  }
  deviation "/pic-notification:upstream-pcm" {
    deviate not-supported;
  }
  deviation "/pic-notification:upstream-pcm-resume" {
    deviate not-supported;
  }
  deviation "/pic-notification:fog-abnormal" {
    deviate not-supported;
  }
  deviation "/pic-notification:fog-abnormal-resume" {
    deviate not-supported;
  }
  deviation "/pic-notification:gate-abnormal" {
    deviate not-supported;
  }
  deviation "/pic-notification:gate-abnormal-resume" {
    deviate not-supported;
  }
  deviation "/pic-notification:gps-module-insert" {
    deviate not-supported;
  }
  deviation "/pic-notification:gps-module-remove" {
    deviate not-supported;
  }
  deviation "/pic-notification:humidity-abnormal" {
    deviate not-supported;
  }
  deviation "/pic-notification:humidity-abnormal-resume" {
    deviate not-supported;
  }
  deviation "/pic-notification:input-error-exceed" {
    deviate not-supported;
  }
  deviation "/pic-notification:input-error-exceed-resume" {
    deviate not-supported;
  }
  deviation "/pic-notification:laser-no-fited" {
    deviate not-supported;
  }
  deviation "/pic-notification:laser-no-fited-resume" {
    deviate not-supported;
  }
  deviation "/pic-notification:laser-shut" {
    deviate not-supported;
  }
  deviation "/pic-notification:laser-shut-resume" {
    deviate not-supported;
  }
  deviation "/pic-notification:license-resource-lack" {
    deviate not-supported;
  }
  deviation "/pic-notification:license-resource-lack-resume" {
    deviate not-supported;
  }
  deviation "/pic-notification:negotiation-failed" {
    deviate not-supported;
  }
  deviation "/pic-notification:negotiation-failed-resume" {
    deviate not-supported;
  }
  deviation "/pic-notification:output-error-exceed" {
    deviate not-supported;
  }
  deviation "/pic-notification:output-error-exceed-resume" {
    deviate not-supported;
  }
  deviation "/pic-notification:crc-error-warning" {
    deviate not-supported;
  }
  deviation "/pic-notification:crc-error-warning-resume" {
    deviate not-supported;
  }
  deviation "/pic-notification:port-mode-change" {
    deviate not-supported;
  }
  deviation "/pic-notification:port-physical-down" {
    deviate not-supported;
  }
  deviation "/pic-notification:port-physical-up" {
    deviate not-supported;
  }
  deviation "/pic-notification:port-type-change" {
    deviate not-supported;
  }
  deviation "/pic-notification:remote-defect" {
    deviate not-supported;
  }
  deviation "/pic-notification:remote-defect-resume" {
    deviate not-supported;
  }
  deviation "/pic-notification:cable-snr-abnormal" {
    deviate not-supported;
  }
  deviation "/pic-notification:cable-snr-abnormal-resume" {
    deviate not-supported;
  }
  deviation "/pic-notification:port-combination-mode-change" {
    deviate not-supported;
  }
  deviation "/pic-notification:channel-associated-signalling-abnormal" {
    deviate not-supported;
  }
  deviation "/pic-notification:channel-associated-signalling-abnormal-resume" {
    deviate not-supported;
  }
  deviation "/pic-notification:port-down" {
    deviate not-supported;
  }
  deviation "/pic-notification:port-up" {
    deviate not-supported;
  }

}
