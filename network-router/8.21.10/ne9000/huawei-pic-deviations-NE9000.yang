/*
Copyright (C) 2021 Huawei Technologies Co., Ltd. All rights reserved.
*/
module huawei-pic-deviations-NE9000 {
  namespace "urn:huawei:yang:huawei-pic-deviations-NE9000";
  prefix pic-devs-NE9000;

  import huawei-pic {
    prefix pic;
  }

  import huawei-extension {
    prefix ext;
  }

  import huawei-driver {
    prefix driver;
  }

  import huawei-devm {
    prefix devm;
  }

  import huawei-license {
    prefix lcs;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic module.";

  revision 2021-05-07 {
    description
      "Initial revision.";
    reference
      "Huawei private.";
  }

  typedef auto-clear-deviations {
    type enumeration {
      enum "physical-mode" {
        value 14;
        description 
          "Physical mode.";
      }
    }
    description 
      "Auto Clear Type.";
  }

  typedef eth-speed-type-deviations {
    type enumeration {
      enum "10M" {
        value 0;
        description 
          "Configure 10M.";
      }
      enum "100M" {
        value 1;
        description 
          "Configure 100M.";
      }
      enum "1000M" {
        value 2;
        description 
          "Configure 1000M.";
      }
      enum "auto" {
        value 9;
        description 
          "Auto.";
      }
    }
    description 
      "Speed type.";
  }

  typedef port-ethernet-fec-mode-deviations {
    type enumeration {
      enum "standard" {
        value 1;
        description 
          "Standard.";
      }
      enum "none" {
        value 0;
        description 
          "None.";
      }
      enum "enhanced" {
        value 2;
        description 
          "Enhanced.";
      }
      enum "enhanced-i-4" {
        value 4;
        description 
          "Enhanced-i-4.";
      }
      enum "enhanced-i-7" {
        value 3;
        description 
          "Enhanced-i-7.";
      }
      enum "lhaul-sd" {
        value 5;
        description 
          "Lhaul-sd.";
      }
    }
    description 
      "Fec mode.";
  }

  typedef port-negotiation-mode-type-deviations {
    type enumeration {
      enum "slave" {
        value 0;
        description 
          "Slave.";
      }
    }
    description 
      "Port negotiation mode.";
  }

  typedef tx-power-cfg-type-deviations {
    type enumeration {
      enum "tx-power-target" {
        value 0;
        description 
          "Optical power configurations enable.";
      }
    }
    description 
      "Optical power cfg type. If the hardware does not support it, returning to the current interface does not support it.";
  }

  deviation "/pic:pic/pic:panel-split-ports/pic:panel-split-port/pic:related-ports" {
    deviate not-supported;
  }
  deviation "/pic:pic/pic:alarm-ais-inserts" {
    deviate not-supported;
  }
  deviation "/pic:pic/pic:port-extends" {
    deviate not-supported;
  }
  deviation "/pic:attr-abort" {
    deviate not-supported;
  }
  deviation "/pic:attr-start" {
    deviate not-supported;
  }
  deviation "/pic:set-port-extend" {
    deviate not-supported;
  }
  deviation "/driver:driver/driver:global-attribute/pic:global/pic:bip8-sd-enable" {
    deviate not-supported;
  }
  deviation "/driver:driver/driver:global-attribute/pic:global/pic:port-down-laser-shut-log-enable" {
    deviate not-supported;
  }
  deviation "/driver:driver/driver:global-attribute/pic:global/pic:driver-mode" {
    deviate not-supported;
  }
  deviation "/driver:driver/driver:global-attribute/pic:global/pic:speed-downgrade" {
    deviate not-supported;
  }
  deviation "/driver:driver/driver:global-attribute/pic:global/pic:cpos-mix-service-mode-enable" {
    deviate not-supported;
  }
  deviation "/devm:devm/devm:ports/devm:port/pic:ethernet/pic:speed-switch-mode" {
    deviate not-supported;
  }
  deviation "/devm:devm/devm:ports/devm:port/pic:ethernet/pic:jumbo-frame" {
    deviate not-supported;
  }
  deviation "/devm:devm/devm:ports/devm:port/pic:ethernet/pic:mru" {
    deviate not-supported;
  }
  deviation "/devm:devm/devm:ports/devm:port/pic:ethernet/pic:inter-packet-gap" {
    deviate not-supported;
  }
  deviation "/devm:devm/devm:ports/devm:port/pic:ethernet/pic:mac-itf-mode" {
    deviate not-supported;
  }
  deviation "/devm:devm/devm:ports/devm:port/pic:ethernet/pic:flexphy-speed" {
    deviate not-supported;
  }
  deviation "/devm:devm/devm:ports/devm:port/pic:ethernet/pic:attenuation" {
    deviate not-supported;
  }
  deviation "/devm:devm/devm:ports/devm:port/pic:ethernet/pic:los-trap-down-hold" {
    deviate not-supported;
  }
  deviation "/devm:devm/devm:ports/devm:port/pic:ethernet/pic:combo" {
    deviate not-supported;
  }
  deviation "/devm:devm/devm:ports/devm:port/pic:ethernet/pic:prefec-ber-coefficient" {
    deviate not-supported;
  }
  deviation "/devm:devm/devm:ports/devm:port/pic:ethernet/pic:prefec-ber-power" {
    deviate not-supported;
  }
  deviation "/devm:devm/devm:ports/devm:port/pic:ethernet/pic:eth-wan-attr/pic:scramble" {
    deviate not-supported;
  }
  deviation "/devm:devm/devm:ports/devm:port/pic:optical-module/pic:vendor-oui" {
    deviate not-supported;
  }
  deviation "/devm:devm/devm:ports/devm:port/pic:optical-module/pic:vendor-rev" {
    deviate not-supported;
  }
  deviation "/devm:devm/devm:ports/devm:port/pic:optical-module/pic:gpon-sn" {
    deviate not-supported;
  }
  deviation "/devm:devm/devm:ports/devm:port/pic:transmission-alarm/pic:threshold-bip2tca" {
    deviate not-supported;
  }
  deviation "/devm:devm/devm:ports/devm:port/pic:pos/pic:speed" {
    deviate not-supported;
  }
  deviation "/devm:devm/devm:ports/devm:port/pic:atm" {
    deviate not-supported;
  }
  deviation "/devm:devm/devm:ports/devm:port/pic:cpos" {
    deviate not-supported;
  }
  deviation "/devm:devm/devm:ports/devm:port/pic:port-alarm/pic:pdh-port-alarm" {
    deviate not-supported;
  }
  deviation "/devm:devm/devm:ports/devm:port/pic:port-alarm/pic:alarm-type/pic:crc-error-threshold/pic:crc-error-threshold/pic:crc-error" {
    deviate not-supported;
  }
  deviation "/devm:devm/devm:ports/devm:port/pic:port-alarm/pic:alarm-type/pic:link-crc/pic:crc-per-warn" {
    deviate not-supported;
  }
  deviation "/devm:devm/devm:ports/devm:port/pic:adm-port" {
    deviate not-supported;
  }
  deviation "/devm:devm/devm:ports/devm:port/pic:phy-serial" {
    deviate not-supported;
  }
  deviation "/devm:devm/devm:ports/devm:port/pic:phy-voice" {
    deviate not-supported;
  }
  deviation "/devm:devm/devm:ports/devm:port/pic:e1t1" {
    deviate not-supported;
  }
  deviation "/devm:devm/devm:ports/devm:port/pic:e3t3" {
    deviate not-supported;
  }
  deviation "/lcs:license/pic:lcs-ports/pic:port-basic/pic:port-band" {
    deviate not-supported;
  }
  deviation "/lcs:license/pic:expand-ports" {
    deviate not-supported;
  }
  deviation "/lcs:license/pic:rtus" {
    deviate not-supported;
  }
  deviation "/lcs:license/pic:rtu-extends" {
    deviate not-supported;
  }
  deviation "/devm:devm/devm:cards/devm:card/pic:card-tdm-param" {
    deviate not-supported;
  }
  deviation "/devm:devm/devm:cards/devm:card/pic:service-mode" {
    deviate not-supported;
  }
  deviation "/devm:devm/devm:cards/devm:card/pic:port-group-modes" {
    deviate not-supported;
  }
  deviation "/devm:devm/devm:cards/devm:card/pic:frame-format" {
    deviate not-supported;
  }
  deviation "/devm:devm/devm:cards/devm:card/pic:em-set" {
    deviate not-supported;
  }
  deviation "/devm:devm/devm:cards/devm:card/pic:service-switch" {
    deviate not-supported;
  }
  deviation "/devm:devm/devm:mpu-boards/devm:mpu-board/pic:cmac-padding" {
    deviate not-supported;
  }
  deviation "/devm:devm/devm:lpu-boards/devm:lpu-board/pic:cmac-padding" {
    deviate not-supported;
  }
  deviation "/devm:devm/devm:cards/devm:card/pic:cmu-switchs" {
    deviate not-supported;
  }
  deviation "/pic:pic/pic:auto-clears/pic:auto-clear/pic:type" {
    deviate replace {
      type pic-devs-NE9000:auto-clear-deviations;
    }
  }
  ext:deviation-ext "/pic:pic/pic:auto-clears/pic:auto-clear/pic:time" {
    ext:deviate-ext replace {
      ext:dynamic-default {
        ext:default-value "20" {
          when "../type = 'physical-mode'";
          description "The default value is 20 when type is physical-mode.";
        }
      }
    }
  }
  deviation "/devm:devm/devm:ports/devm:port/pic:ethernet/pic:speed" {
    deviate replace {
      type pic-devs-NE9000:eth-speed-type-deviations;
    }
  }
  deviation "/devm:devm/devm:ports/devm:port/pic:ethernet/pic:negotiation-mode" {
    deviate replace {
      type pic-devs-NE9000:port-negotiation-mode-type-deviations;
    }
  }
  deviation "/devm:devm/devm:ports/devm:port/pic:ethernet/pic:tx-power-cfg-type" {
    deviate replace {
      type pic-devs-NE9000:tx-power-cfg-type-deviations;
    }
  }
  deviation "/devm:devm/devm:ports/devm:port/pic:ethernet/pic:fec-mode" {
    deviate replace {
      type pic-devs-NE9000:port-ethernet-fec-mode-deviations;
    }
  }
  deviation "/devm:devm/devm:ports/devm:port/pic:port-alarm/pic:alarm-type/pic:crc-error-threshold/pic:crc-error-threshold/pic:crc-error-interval" {
    deviate add {
      must "not(../crc-error-percent-alm-thr)";
    }
  }
  deviation "/devm:devm/devm:ports/devm:port/pic:port-alarm/pic:alarm-type/pic:link-crc/pic:crc-per-alarm/pic:crc-per-alm-thr-power" {
    deviate replace {
      type uint32 {
        range "1..5";
      }
    }
  }
  deviation "/devm:devm/devm:ports/devm:port/pic:port-alarm/pic:alarm-type/pic:link-crc/pic:crc-per-alarm/pic:crc-per-rsum-thr-power" {
    deviate replace {
      type uint32 {
        range "1..6";
      }
    }
  }

}
