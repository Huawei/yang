/*
Copyright (C) 2021 Huawei Technologies Co., Ltd. All rights reserved.
*/
module huawei-pp4-deviations-NE9000 {
  namespace "urn:huawei:yang:huawei-pp4-deviations-NE9000";
  prefix pp4-devs-NE9000;

  import huawei-pp4 {
    prefix pp4;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-pp4 module.";

  revision 2021-05-07 {
    description
      "Initial revision.";
    reference "Huawei private.";
  }

  deviation "/ifm:ifm/ifm:interfaces/ifm:interface/pp4:ip-fwd-broadcast" {
    deviate not-supported;
  }
}
