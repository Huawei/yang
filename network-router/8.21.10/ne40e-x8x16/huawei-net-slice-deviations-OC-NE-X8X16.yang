/*
Copyright (C) 2021 Huawei Technologies Co., Ltd. All rights reserved.
*/
module huawei-net-slice-deviations-OC-NE-X8X16 {
  namespace "urn:huawei:yang:huawei-net-slice-deviations-OC-NE-X8X16";
  prefix net-slice-devs-OC-NE-X8X16;

  import huawei-net-slice {
    prefix net-slice;
  }
  import huawei-if-ip {
    prefix if-ip;
  }
  import huawei-ifm {
    prefix ifm;
  }
  import huawei-ip {
    prefix ip;
  }
  import huawei-network-instance {
    prefix ni;
  }

  organization
    "Huawei Technologies Co., Ltd.";
  contact
    "Huawei Industrial Base
     Bantian, Longgang
     Shenzhen 518129
     People's Republic of China
     Website: http://www.huawei.com
     Email: support@huawei.com";
  description
    "This module defines deviation statements for huawei-net-slice module.";

  revision 2021-05-07 {
    description
      "Initial revision.";
    reference "Huawei private.";
  }

  deviation "/ifm:ifm/ifm:interfaces/ifm:interface/net-slice:net-slice-binding/net-slice:slice-id" {
    deviate delete {
      must '../../ip:ipv6';
    }
    deviate add {
      must '../../ip:ipv6 or /ni:network-instance/ni:instances/ni:instance/if-ip:ipv6-ifs/if-ip:ipv6-if[if-ip:name=current()/../../ifm:name]';
    }
  }
  deviation "/ifm:ifm/ifm:interfaces/ifm:interface/net-slice:net-slices/net-slice:net-slice/net-slice:mode/net-slice:data-plane-mode/net-slice:data-plane" {
    deviate delete {
      must '../../../ip:ipv6 and (../../../ip:ipv6/ip:addresses/ip:address/ip:ip or ../../../net-slice:net-slice-binding)';
    }
    deviate add {
      must '(../../../ip:ipv6 or /ni:network-instance/ni:instances/ni:instance/if-ip:ipv6-ifs/if-ip:ipv6-if[if-ip:name=current()/../../../ifm:name]) and ((../../../ip:ipv6/ip:addresses/ip:address/ip:ip or /ni:network-instance/ni:instances/ni:instance/if-ip:ipv6-ifs/if-ip:ipv6-if/if-ip:addresses/if-ip:address/if-ip:ip) or ../../../net-slice:net-slice-binding)';
    }
  }
  deviation "/ifm:ifm/ifm:interfaces/ifm:interface/net-slice:net-slices/net-slice:net-slice/net-slice:mode/net-slice:flex-channel-mode/net-slice:flex-channel" {
    deviate delete {
      must '../../../ip:ipv6 and (../../../ip:ipv6/ip:addresses/ip:address/ip:ip or ../../../net-slice:net-slice-binding)';
    }
    deviate add {
      must '(../../../ip:ipv6 or /ni:network-instance/ni:instances/ni:instance/if-ip:ipv6-ifs/if-ip:ipv6-if[if-ip:name=current()/../../../ifm:name]) and ((../../../ip:ipv6/ip:addresses/ip:address/ip:ip or /ni:network-instance/ni:instances/ni:instance/if-ip:ipv6-ifs/if-ip:ipv6-if/if-ip:addresses/if-ip:address/if-ip:ip) or ../../../net-slice:net-slice-binding)';
    }
  }
}
