/*
Copyright (C) 2021 Huawei Technologies Co., Ltd. All rights reserved.
*/
module huawei-mpls-notification-deviations-OC-NE-X8X16 {
  namespace "urn:huawei:yang:huawei-mpls-notification-deviations-OC-NE-X8X16";
  prefix mpls-notification-devs-OC-NE-X8X16;

  import huawei-mpls-notification {
    prefix mpls-notification;
  }

  organization
    "Huawei Technologies Co., Ltd.";
  contact
    "Huawei Industrial Base
     Bantian, Longgang
     Shenzhen 518129
     People's Republic of China
     Website: http://www.huawei.com
     Email: support@huawei.com";
  description
    "This module defines deviation statements for huawei-mpls-notification module.";

  revision 2021-05-07 {
    description
      "Initial revision.";
    reference "Huawei private.";
  }

  deviation "/mpls-notification:mpls-slot-res-total-count-exceed" {
    deviate not-supported;
  }
  deviation "/mpls-notification:mpls-slot-res-total-count-exceed-clear" {
    deviate not-supported;
  }
}
