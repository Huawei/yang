/*
Copyright (C) 2019 Huawei Technologies Co., Ltd. All rights reserved.
*/
module huawei-ospfv3-srv6 {
  namespace "urn:huawei:yang:huawei-ospfv3-srv6";
  prefix ospfv3-srv6;
  import huawei-network-instance {
    prefix ni;
  }
  import huawei-ospfv3 {
    prefix ospfv3;
  }
  import huawei-srv6 {
    prefix srv6;
  }
  import huawei-extension {
    prefix ext;
  }
  
  organization
    "Huawei Technologies Co., Ltd.";
  contact
    "Huawei Industrial Base
     Bantian, Longgang
     Shenzhen 518129
     People's Republic of China
     Website: http://www.huawei.com
     Email: support@huawei.com";
  description
    "The YANG module defines generic configuration model for IPv6 Segment Routing (SRv6) OSPFv3 extensions that are common across all of the vendor implementations.";
  revision 2019-12-24 {
    description
      "Initial revision.";
    reference
      "Huawei private.";
  }
  ext:task-name  "ospf";
  augment /ni:network-instance/ni:instances/ni:instance/ospfv3:ospfv3/ospfv3:sites/ospfv3:site {
    description
      "This augments OSPFv3 protocol configuration with SRv6.";
    container srv6 {
      when "../../../../ni:name='_public_'";
      description
        "Configure OSPFv3 IPv6 Segment Routing (SRv6).";
      container locators {
      description
        "List of the information about segment-routing IPv6 locators.";
          list locator {
          key "locator-name";
          description
          "Configure IPv6 Segment Routing (SRv6) locators.";
          leaf locator-name {
            type leafref {
              path "/ni:network-instance/ni:instances/ni:instance/srv6:srv6/srv6:locators/srv6:locator/srv6:name";
            }
            must "../../../../../../../srv6:srv6/srv6:locators/srv6:locator[srv6:name = current()]/srv6:flex-algo=0";
            description
              "Enable OSPFv3 IPv6 Segment Routing (SRv6) with a specified locator.";
          }
          leaf auto-sid {
            type boolean;
            default "true";
            description
              "Enable/disable dynamic SID allocation.";
          }
        }
      }
      container avoid-microloop {
        when "../locators/locator";
        description
          "Configure IPv6 segment routing avoid microloop.";
        leaf enable {
          type boolean;
          default "false";
          description
            "Enable/disable IPv6 segment routing avoid microloop.";
        }
        leaf delay-value {
          type uint16 {
            range "1000..60000";
          }
          units "ms";
          default "5000";
          description
            "Set the route delivery delay for IPv6 segment routing avoid microloop.";
        }
      }
    }
  }
}
