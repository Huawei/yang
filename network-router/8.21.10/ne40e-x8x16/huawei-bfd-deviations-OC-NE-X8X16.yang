/*
Copyright (C) 2021 Huawei Technologies Co., Ltd. All rights reserved.
*/
module huawei-bfd-deviations-OC-NE-X8X16 {
  namespace "urn:huawei:yang:huawei-bfd-deviations-OC-NE-X8X16";
  prefix bfd-devs-OC-NE-X8X16;

  import huawei-bfd {
    prefix bfd;
  }
  import huawei-devm {
    prefix devm;
  }

  organization
    "Huawei Technologies Co., Ltd.";
  contact
    "Huawei Industrial Base
     Bantian, Longgang
     Shenzhen 518129
     People's Republic of China
     Website: http://www.huawei.com
     Email: support@huawei.com";
  description
    "This module defines deviation statements for huawei-bfd module.";

  revision 2021-05-07 {
    description
      "Initial revision.";
    reference "Huawei private.";
  }

  typedef display-type-deviations {
    type enumeration {
      enum all {
        value 0;
        description
          "All BFD sessions.";
      }
      enum discriminator {
        value 4;
        description
          "Discriminator-specified BFD session.";
      }
    }
    description
      "BFD session type.";
  }

  deviation "/bfd:bfd/bfd:global/bfd:process-mode" {
    deviate not-supported;
  }
  deviation "/bfd:bfd/bfd:global/bfd:process-central-slot" {
    deviate not-supported;
  }
  deviation "/bfd:bfd/bfd:global/bfd:process-central-slot2" {
    deviate not-supported;
  }
  deviation "/bfd:bfd/bfd:sessions/bfd:session/bfd:session-type/bfd:static/bfd:static-session-link-type/bfd:ip/bfd:ip-address-type/bfd:ipv4/bfd:multicast-or-unicast-ip/bfd:multicast/bfd:lag-multicast-ipv4" {
    deviate not-supported;
  }
  deviation "/bfd:bfd/bfd:sessions/bfd:session/bfd:session-type/bfd:static/bfd:static-session-link-type/bfd:ip/bfd:ip-address-type/bfd:ipv4/bfd:multicast-or-unicast-ip/bfd:multicast/bfd:unlimited-nego-multicast-ipv4" {
    deviate not-supported;
  }
  deviation "/bfd:bfd/bfd:sessions/bfd:session/bfd:session-type/bfd:static/bfd:static-session-link-type/bfd:ip/bfd:ip-address-type/bfd:ipv4/bfd:multicast-or-unicast-ip/bfd:unicast/bfd:per-link-static-unicast-ipv4" {
    deviate not-supported;
  }
  deviation "/bfd:bfd/bfd:sessions/bfd:session/bfd:session-type/bfd:auto/bfd:auto-session-link-type/bfd:vxlan/bfd:min-tx-interval-auto-vxlan" {
    deviate not-supported;
  }
  deviation "/bfd:bfd/bfd:sessions/bfd:session/bfd:session-type/bfd:auto/bfd:auto-session-link-type/bfd:vxlan/bfd:min-rx-interval-auto-vxlan" {
    deviate not-supported;
  }
  deviation "/bfd:bfd/bfd:sessions/bfd:session/bfd:session-type/bfd:auto/bfd:auto-session-link-type/bfd:vxlan/bfd:destination-address-auto-vxlan" {
    deviate not-supported;
  }
  deviation "/bfd:bfd/bfd:sessions/bfd:session/bfd:session-type/bfd:auto/bfd:auto-session-link-type/bfd:vxlan/bfd:source-address-auto-vxlan" {
    deviate not-supported;
  }
  deviation "/bfd:bfd/bfd:sessions/bfd:session/bfd:session-type/bfd:auto/bfd:auto-session-link-type/bfd:vxlan/bfd:peer-mac-auto-vxlan" {
    deviate not-supported;
  }
  deviation "/bfd:bfd/bfd:sessions/bfd:session/bfd:running/bfd:remote-demand-mode" {
    deviate not-supported;
  }
  deviation "/bfd:bfd/bfd:sessions/bfd:session/bfd:running/bfd:acl-num" {
    deviate not-supported;
  }
  deviation "/bfd:bfd/bfd:sessions/bfd:session/bfd:running/bfd:echo-tx-timer-id" {
    deviate not-supported;
  }
  deviation "/bfd:bfd/bfd:statistics/bfd:vxlan-session-num" {
    deviate not-supported;
  }
  deviation "/bfd:bfd/bfd:all-sessions/bfd:all-session/bfd:demand-enable" {
    deviate not-supported;
  }
  deviation "/bfd:bfd/bfd:all-sessions/bfd:all-session/bfd:lag" {
    deviate not-supported;
  }
  deviation "/bfd:bfd/bfd:all-sessions/bfd:all-session/bfd:running/bfd:remote-demand-mode" {
    deviate not-supported;
  }
  deviation "/bfd:bfd/bfd:all-sessions/bfd:all-session/bfd:running/bfd:acl-num" {
    deviate not-supported;
  }
  deviation "/bfd:bfd/bfd:all-sessions/bfd:all-session/bfd:running/bfd:echo-tx-timer-id" {
    deviate not-supported;
  }
  deviation "/bfd:bfd/bfd:mul-cast-sessions/bfd:mul-cast-session/bfd:multi-cast-session-running/bfd:re-demand-mode" {
    deviate not-supported;
  }
  deviation "/bfd:bfd/bfd:mul-cast-sessions/bfd:mul-cast-session/bfd:multi-cast-session-running/bfd:acl-num" {
    deviate not-supported;
  }
  deviation "/bfd:bfd/bfd:mul-cast-sessions/bfd:mul-cast-session/bfd:multi-cast-session-running/bfd:echo-tx-timer-id" {
    deviate not-supported;
  }
  deviation "/bfd:bfd/bfd:sessions/bfd:session/bfd:session-type/bfd:static/bfd:static-session-link-type/bfd:ip/bfd:ip-address-type/bfd:ipv4/bfd:select-board-slot-static-ipv4" {
    deviate replace {
      type leafref {
        path "/devm:devm/devm:lpu-boards/devm:lpu-board/devm:position";
      }
    }
  }
  deviation "/bfd:bfd/bfd:sessions/bfd:session/bfd:session-type/bfd:static/bfd:static-session-link-type/bfd:ip/bfd:ip-address-type/bfd:ipv4/bfd:select-board-slot2-static-ipv4" {
    deviate replace {
      type leafref {
        path "/devm:devm/devm:lpu-boards/devm:lpu-board/devm:position";
      }
    }
  }
  deviation "/bfd:bfd/bfd:sessions/bfd:session/bfd:session-type/bfd:static/bfd:static-session-link-type/bfd:ip/bfd:ip-address-type/bfd:ipv6/bfd:select-board-slot-static-ipv6" {
    deviate replace {
      type leafref {
        path "/devm:devm/devm:lpu-boards/devm:lpu-board/devm:position";
      }
    }
    deviate add {
      must 'not(../bfd:out-if-name-static-ipv6)';
    }
  }
  deviation "/bfd:bfd/bfd:sessions/bfd:session/bfd:session-type/bfd:static/bfd:static-session-link-type/bfd:ip/bfd:ip-address-type/bfd:ipv6/bfd:select-board-slot2-static-ipv6" {
    deviate replace {
      type leafref {
        path "/devm:devm/devm:lpu-boards/devm:lpu-board/devm:position";
      }
    }
  }
  deviation "/bfd:bfd/bfd:sessions/bfd:session/bfd:session-type/bfd:auto/bfd:auto-session-link-type/bfd:ip/bfd:address-type/bfd:ipv4/bfd:select-board-slot-auto-ipv4" {
    deviate replace {
      type leafref {
        path "/devm:devm/devm:lpu-boards/devm:lpu-board/devm:position";
      }
    }
    deviate add {
      must 'not(../bfd:out-if-name-auto-ip)';
    }
  }
  deviation "/bfd:bfd/bfd:sessions/bfd:session/bfd:session-type/bfd:auto/bfd:auto-session-link-type/bfd:ip/bfd:address-type/bfd:ipv4/bfd:select-board-slot2-auto-ipv4" {
    deviate replace {
      type leafref {
        path "/devm:devm/devm:lpu-boards/devm:lpu-board/devm:position";
      }
    }
  }
  deviation "/bfd:bfd/bfd:sessions/bfd:session/bfd:session-type/bfd:auto/bfd:auto-session-link-type/bfd:ip/bfd:address-type/bfd:ipv6/bfd:select-board-slot-auto-ipv6" {
    deviate replace {
      type leafref {
        path "/devm:devm/devm:lpu-boards/devm:lpu-board/devm:position";
      }
    }
    deviate add {
      must 'not(../bfd:out-if-name-auto-ip)';
    }
  }
  deviation "/bfd:bfd/bfd:sessions/bfd:session/bfd:session-type/bfd:auto/bfd:auto-session-link-type/bfd:ip/bfd:address-type/bfd:ipv6/bfd:select-board-slot2-auto-ipv6" {
    deviate replace {
      type leafref {
        path "/devm:devm/devm:lpu-boards/devm:lpu-board/devm:position";
      }
    }
  }
  deviation "/bfd:bfd/bfd:sessions/bfd:session/bfd:groups/bfd:group/bfd:sub-select-slot-id" {
    deviate replace {
      type leafref {
        path "/devm:devm/devm:lpu-boards/devm:lpu-board/devm:position";
      }
    }
  }
  deviation "/bfd:bfd/bfd:sbfd/bfd:authentication-keys/bfd:authentication-key/bfd:session-type" {
    deviate add {
      must "(contains(../destination-address,':') and (../session-type='sbfd-ip-multi-hop' or ../session-type='sbfd-sr-te-policy-segment-list')) or (not(contains(../destination-address,':')) and (../session-type='sbfd-lsp-tunnel' or ../session-type='sbfd-sr-te-policy-segment-list'))";
    }
  }
  deviation "/bfd:bfd/bfd:authentication-keys/bfd:authentication-key/bfd:session-type" {
    deviate add {
      must "(contains(../peer-ip,':') and (../session-type='ip-single-hop' or ../session-type='ip-multi-hop')) or (not(contains(../peer-ip,':')) and (../session-type='ip-single-hop' or ../session-type='ip-multi-hop' or ../session-type='mpls-passive' or ../session-type='lsp-tunnel'))";
    }
  }
  deviation "/bfd:reset-bfd-statistics/bfd:input/bfd:reset-type" {
    deviate replace {
      type bfd-devs-OC-NE-X8X16:display-type-deviations;
    }
  }
}
