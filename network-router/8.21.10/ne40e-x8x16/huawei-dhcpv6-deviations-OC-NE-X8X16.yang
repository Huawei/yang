/*
Copyright (C) 2021 Huawei Technologies Co., Ltd. All rights reserved.
*/
module huawei-dhcpv6-deviations-OC-NE-X8X16 {
  namespace "urn:huawei:yang:huawei-dhcpv6-deviations-OC-NE-X8X16";
  prefix dhcpv6-devs-OC-NE-X8X16;

  import huawei-dhcpv6 {
    prefix dhcpv6;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-dhcpv6 module.";

  revision 2021-05-07 {
    description
      "Initial revision.";
    reference "Huawei private.";
  }

  typedef dhcpv6-duid-deviations {
    type enumeration {
      enum invalid {
        value 0;
        description
          "-";
      }
      enum llt {
        value 1;
        description
          "Link-layer address plus time.";
      }
      enum user-defined {
        value 3;
        description
          "User-defined.";
      }
    }
    description
      "Description of dhcp6_dhcpv6Duid_type.";
  }

  deviation "/dhcpv6:reset-dhcpv6-snooping-packet-statistics" {
    deviate not-supported;
  }
  deviation "/dhcpv6:reset-dhcpv6-snooping-discarded-packet-statistics" {
    deviate not-supported;
  }
  deviation "/dhcpv6:reset-dhcpv6-snooping-dynamic-binding-table" {
    deviate not-supported;
  }
  deviation "/ifm:ifm/ifm:interfaces/ifm:interface/dhcpv6:dhcpv6-relay-attribute/dhcpv6:rebuild-option" {
    deviate not-supported;
  }
  deviation "/dhcpv6:dhcpv6/dhcpv6:common/dhcpv6:global/dhcpv6:duid-format" {
    deviate replace {
      type dhcpv6-devs-OC-NE-X8X16:dhcpv6-duid-deviations;
    }
  }
  deviation "/dhcpv6:dhcpv6/dhcpv6:common/dhcpv6:session-car/dhcpv6:cir-value" {
    deviate replace {
      default "1024";
    }
  }
  deviation "/dhcpv6:dhcpv6/dhcpv6:common/dhcpv6:session-car/dhcpv6:cbs-value" {
    deviate replace {
      default "128000";
    }
  }
  deviation "/dhcpv6:dhcpv6/dhcpv6:common/dhcpv6:session-car/dhcpv6:pir-value" {
    deviate replace {
      default "2048";
    }
  }
  deviation "/dhcpv6:dhcpv6/dhcpv6:common/dhcpv6:session-car/dhcpv6:pbs-value" {
    deviate replace {
      default "256000";
    }
  }
  deviation "/ifm:ifm/ifm:interfaces/ifm:interface/dhcpv6:dhcpv6-relay-attribute" {
    deviate add {
      must '(count(destination-addresses/destination-address) + count(destination-ifs/destination-if)) <= 8';
    }
  }
}
