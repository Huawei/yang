/*
Copyright (C) 2021 Huawei Technologies Co., Ltd. All rights reserved.
*/
module huawei-pki-deviations-OC-NE-X8X16 {
  namespace "urn:huawei:yang:huawei-pki-deviations-OC-NE-X8X16";
  prefix pki-devs-OC-NE-X8X16;

  import huawei-pki {
    prefix pki;
  }

  organization
    "Huawei Technologies Co., Ltd.";
  contact
    "Huawei Industrial Base
     Bantian, Longgang
     Shenzhen 518129
     People's Republic of China
     Website: http://www.huawei.com
     Email: support@huawei.com";
  description
    "This module defines deviation statements for huawei-pki module.";

  revision 2021-05-07 {
    description
      "Initial revision.";
    reference "Huawei private.";
  }

  deviation "/pki:certificate-import" {
    deviate not-supported;
  }
  deviation "/pki:certificate-delete" {
    deviate not-supported;
  }
}
