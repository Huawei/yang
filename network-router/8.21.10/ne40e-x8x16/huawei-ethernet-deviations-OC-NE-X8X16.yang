/*
Copyright (C) 2020 Huawei Technologies Co., Ltd. All rights reserved.
*/
module huawei-ethernet-deviations-OC-NE-X8X16 {
  namespace "urn:huawei:yang:huawei-ethernet-deviations-OC-NE-X8X16";
  prefix ethernet-devs-OC-NE-X8X16;

  import huawei-ethernet {
    prefix ethernet;
  }
  import huawei-ifm {
    prefix ifm;
  }
  import huawei-vlan {
    prefix vlan;
  }

  organization
    "Huawei Technologies Co., Ltd.";
  contact
    "Huawei Industrial Base
     Bantian, Longgang
     Shenzhen 518129
     People's Republic of China
     Website: http://www.huawei.com
     Email: support@huawei.com";
  description
    "VLAN member interfaces and QinQ.";

  revision 2020-04-26 {
    description
      "Initial revision.";
    reference "Huawei private.";
  }

  deviation "/ethernet:ethernet" {
    deviate not-supported;
  }
  deviation "/ifm:ifm/ifm:interfaces/ifm:interface/ethernet:ethernet/ethernet:main-interface/ethernet:port-isolate-groups" {
    deviate not-supported;
  }
  deviation "/ifm:ifm/ifm:interfaces/ifm:interface/ethernet:ethernet/ethernet:main-interface/ethernet:port-am-isolates" {
    deviate not-supported;
  }
  deviation "/ifm:ifm/ifm:interfaces/ifm:interface/ethernet:ethernet/ethernet:main-interface/ethernet:l2-attribute/ethernet:untag-vlans" {
    deviate not-supported;
  }
  deviation "/ifm:ifm/ifm:interfaces/ifm:interface/ethernet:ethernet/ethernet:l2-sub-interface/ethernet:flow-type/ethernet:qinq/ethernet:qinqs/ethernet:qinq-with-pe-segments" {
    deviate not-supported;
  }
  deviation "/ifm:ifm/ifm:interfaces/ifm:interface/ethernet:ethernet/ethernet:main-interface/ethernet:l2-attribute/ethernet:vlan-stacking-remarks" {
    deviate not-supported;
  }
  deviation "/ifm:ifm/ifm:interfaces/ifm:interface/ethernet:ethernet/ethernet:main-interface/ethernet:l2-attribute/ethernet:vlan-mapping-remarks" {
    deviate not-supported;
  }
  deviation "/ifm:ifm/ifm:interfaces/ifm:interface/ethernet:ethernet/ethernet:main-interface/ethernet:l2-attribute/ethernet:vlan-mappings/ethernet:vlan-mapping/ethernet:mapping-vlan" {
    deviate add {
      must "/vlan:vlan/vlan:vlans/vlan:vlan[vlan:id=current()]/vlan:type!='super'";
    }
  }
  deviation "/ifm:ifm/ifm:interfaces/ifm:interface/ethernet:ethernet/ethernet:l3-sub-interface/ethernet:flow-type/ethernet:qinq-termination/ethernet:qinq-termination/ethernet:remark-8021p/ethernet:remark-type" {
    deviate add {
      must "(../remark-type='trust-pe-8021p') or (/ifm:ifm/ifm:interfaces/ifm:interface[ifm:name=current()/../../../../../ifm:name]/ifm:type!='PW-VE')";
    }
  }
  deviation "/ifm:ifm/ifm:interfaces/ifm:interface/ethernet:ethernet/ethernet:main-interface/ethernet:encapsulation/ethernet:pvid" {
    deviate replace {
      type uint16 {
        range "1..4094";
      }
    }
  }
  deviation "/ifm:ifm/ifm:interfaces/ifm:interface/ethernet:ethernet/ethernet:main-interface/ethernet:l2-attribute/ethernet:vlan-classification" {
    deviate not-supported;
  }
}
