/*
Copyright (C) 2020 Huawei Technologies Co., Ltd. All rights reserved.
*/
module huawei-oam-cfm-interface {
  namespace "urn:huawei:yang:huawei-oam-cfm-interface";
  prefix oam-cfm-interface;
  
  import huawei-extension {
    prefix ext;
  }
  import huawei-oammgr {
    prefix oammgr;
  }
  import huawei-ifm {
    prefix ifm;
  }
  import huawei-y1731 {
    prefix y1731;
  }
  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";
  revision 2020-09-18 {
    description
      "Initial revision.";
    reference
      "Huawei private.";
  }
  ext:task-name  "oammgr";
  typedef cfm-bind-interface-type {
    type enumeration {
      enum "CFM-IF" {
        value 1;
        description
          "Type that CFM transfers fault information to interface.";
      }
      enum "IF-CFM" {
        value 2;
        description
          "Type that interface transfers fault information to CFM.";
      }
    }
    description
      "Binding type.";
  }
  typedef trigger-type {
    type enumeration {
      enum "if-down" {
        value 0;
        description
          "Shutdown the interface.";
      }
      enum "if-notify" {
        value 1;
        description
          "Notify OAM status.";
      }
    }
    description
      "Trigger type.";
  }
  augment "/oammgr:oammgr" {
    description
      "Configure the operation, administration and maintenance (OAM) association function.";
    container cfm-bind-interfaces {
      description
        "List of associations between CFM and interface.";
      list cfm-bind-interface {
        key "md-name ma-name if-name bind-type";
        unique "md-name ma-name bind-type";
        unique "if-name bind-type";
        description
          "Configure an instance of an association between CFM and interface.";
        leaf md-name {
          type leafref {
            path "/y1731:y1731/y1731:global-enable/y1731:mds/y1731:md/y1731:name";
          }
          description
            "Configure a MD name.";
        }
        leaf ma-name {
          type leafref {
            path "/y1731:y1731/y1731:global-enable/y1731:mds/y1731:md[y1731:name=current()/../md-name]/y1731:mas/y1731:ma/y1731:name";
          }
          description
            "Configure a MA name.";
        }
        leaf if-name {
          type leafref {
            path "/ifm:ifm/ifm:interfaces/ifm:interface/ifm:name";
          }
          description
            "Configure the name of interface.";
        }
        leaf bind-type {
          type cfm-bind-interface-type;
          description
            "Configure a binding type.";
        }
        leaf trigger-type {
          type trigger-type;
          must "../trigger-type='if-down' or ../bind-type='CFM-IF'";
          default "if-down";
          description
            "Configure the trigger type.";
        }
      }
    }
  }
}
