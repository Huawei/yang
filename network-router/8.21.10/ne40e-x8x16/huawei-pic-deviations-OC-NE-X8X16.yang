/*
Copyright (C) 2021 Huawei Technologies Co., Ltd. All rights reserved.
*/
module huawei-pic-deviations-OC-NE-X8X16 {
  namespace "urn:huawei:yang:huawei-pic-deviations-OC-NE-X8X16";
  prefix pic-devs-OC-NE-X8X16;

  import huawei-pic {
    prefix pic;
  }

  import huawei-extension {
    prefix ext;
  }

  import huawei-driver {
    prefix driver;
  }

  import huawei-devm {
    prefix devm;
  }

  import huawei-license {
    prefix lcs;
  }

  organization
    "Huawei Technologies Co., Ltd.";

  contact
    "Huawei Industrial Base
     Bantian, Longgang
     Shenzhen 518129
     People's Republic of China
     Website: http://www.huawei.com
     Email: support@huawei.com";

  description
    "This module defines deviation statements for huawei-pic module.";

  revision 2021-05-07 {
    description
      "Initial revision.";
    reference
      "Huawei private.";
  }

  typedef alarm-ais-insert-name-deviations {
    type enumeration {
      enum "hptim" {
        value 1;
        description 
          "Hptim.";
      }
      enum "lptim" {
        value 2;
        description 
          "Lptim.";
      }
      enum "rstim" {
        value 3;
        description 
          "Rstim.";
      }
      enum "hpuneq" {
        value 6;
        description 
          "Hpuneq.";
      }
      enum "hpplm" {
        value 7;
        description 
          "Hpplm.";
      }
      enum "lpuneq" {
        value 8;
        description 
          "Lpuneq.";
      }
    }
    description 
      "Alarm Name.";
  }

  typedef auto-clear-deviations {
    type enumeration {
      enum "physical-mode" {
        value 14;
        description 
          "Physical mode.";
      }
    }
    description 
      "Auto Clear Type.";
  }

  typedef card-port-group-mode-type-deviations {
    type enumeration {
      enum "25GE-10GE" {
        value 1;
        description 
          "Configure 25GE-10GE.";
      }
      enum "10GE-1GE" {
        value 2;
        description 
          "Configure 10GE-1GE.";
      }
    }
    description 
      "Switch mode.";
  }

  typedef card-service-mode-deviations {
    type enumeration {
      enum "POS-8X622M" {
        value 12;
        description 
          "Eight 622M POS port.";
      }
      enum "POS-4X2.5G" {
        value 13;
        description 
          "Four 2.5G POS port.";
      }
      enum "POS-1X10G" {
        value 14;
        description 
          "One 10G POS port.";
      }
      enum "POS-8X155M" {
        value 15;
        description 
          "Eight 155M POS port.";
      }
    }
    description 
      "Bandwidth Mode. Modifying the configuration affects the instances of ports and interfaces. For details about the impact, see the description of each enumerated item.";
  }

  typedef eth-speed-type-deviations {
    type enumeration {
      enum "10M" {
        value 0;
        description 
          "Configure 10M.";
      }
      enum "100M" {
        value 1;
        description 
          "Configure 100M.";
      }
      enum "1000M" {
        value 2;
        description 
          "Configure 1000M.";
      }
      enum "auto" {
        value 9;
        description 
          "Auto.";
      }
    }
    description 
      "Speed type.";
  }

  typedef port-negotiation-mode-type-deviations {
    type enumeration {
      enum "slave" {
        value 0;
        description 
          "Slave.";
      }
    }
    description 
      "Port negotiation mode.";
  }

  deviation "/pic:pic/pic:panel-split-ports/pic:panel-split-port/pic:related-ports" {
    deviate not-supported;
  }
  deviation "/pic:pic/pic:port-extends" {
    deviate not-supported;
  }
  deviation "/pic:attr-abort" {
    deviate not-supported;
  }
  deviation "/pic:attr-start" {
    deviate not-supported;
  }
  deviation "/pic:set-port-extend" {
    deviate not-supported;
  }
  deviation "/driver:driver/driver:global-attribute/pic:global/pic:port-down-laser-shut-log-enable" {
    deviate not-supported;
  }
  deviation "/driver:driver/driver:global-attribute/pic:global/pic:speed-downgrade" {
    deviate not-supported;
  }
  deviation "/devm:devm/devm:ports/devm:port/pic:ethernet/pic:mru" {
    deviate not-supported;
  }
  deviation "/devm:devm/devm:ports/devm:port/pic:ethernet/pic:inter-packet-gap" {
    deviate not-supported;
  }
  deviation "/devm:devm/devm:ports/devm:port/pic:ethernet/pic:mac-itf-mode" {
    deviate not-supported;
  }
  deviation "/devm:devm/devm:ports/devm:port/pic:ethernet/pic:los-trap-down-hold" {
    deviate not-supported;
  }
  deviation "/devm:devm/devm:ports/devm:port/pic:ethernet/pic:combo" {
    deviate not-supported;
  }
  deviation "/devm:devm/devm:ports/devm:port/pic:ethernet/pic:prefec-ber-coefficient" {
    deviate not-supported;
  }
  deviation "/devm:devm/devm:ports/devm:port/pic:ethernet/pic:prefec-ber-power" {
    deviate not-supported;
  }
  deviation "/devm:devm/devm:ports/devm:port/pic:ethernet/pic:eth-wan-attr/pic:scramble" {
    deviate not-supported;
  }
  deviation "/devm:devm/devm:ports/devm:port/pic:optical-module/pic:vendor-oui" {
    deviate not-supported;
  }
  deviation "/devm:devm/devm:ports/devm:port/pic:optical-module/pic:vendor-rev" {
    deviate not-supported;
  }
  deviation "/devm:devm/devm:ports/devm:port/pic:optical-module/pic:gpon-sn" {
    deviate not-supported;
  }
  deviation "/devm:devm/devm:ports/devm:port/pic:transmission-alarm/pic:threshold-bip2tca" {
    deviate not-supported;
  }
  deviation "/devm:devm/devm:ports/devm:port/pic:atm" {
    deviate not-supported;
  }
  deviation "/devm:devm/devm:ports/devm:port/pic:port-alarm/pic:alarm-type/pic:crc-error-threshold/pic:crc-error-threshold/pic:crc-error" {
    deviate not-supported;
  }
  deviation "/devm:devm/devm:ports/devm:port/pic:port-alarm/pic:alarm-type/pic:link-crc/pic:crc-per-warn" {
    deviate not-supported;
  }
  deviation "/devm:devm/devm:ports/devm:port/pic:phy-serial" {
    deviate not-supported;
  }
  deviation "/devm:devm/devm:ports/devm:port/pic:phy-voice" {
    deviate not-supported;
  }
  deviation "/devm:devm/devm:ports/devm:port/pic:e1t1/pic:bipv-static" {
    deviate not-supported;
  }
  deviation "/devm:devm/devm:ports/devm:port/pic:e1t1/pic:fas-static" {
    deviate not-supported;
  }
  deviation "/devm:devm/devm:ports/devm:port/pic:e1t1/pic:crc-static" {
    deviate not-supported;
  }
  deviation "/devm:devm/devm:ports/devm:port/pic:e3t3" {
    deviate not-supported;
  }
  deviation "/lcs:license/pic:upgrade-ports" {
    deviate not-supported;
  }
  deviation "/lcs:license/pic:expand-ports" {
    deviate not-supported;
  }
  deviation "/lcs:license/pic:rtu-extends" {
    deviate not-supported;
  }
  deviation "/devm:devm/devm:cards/devm:card/pic:card-tdm-param/pic:impedance" {
    deviate not-supported;
  }
  deviation "/devm:devm/devm:cards/devm:card/pic:service-mode/pic:portrate" {
    deviate not-supported;
  }
  deviation "/devm:devm/devm:cards/devm:card/pic:frame-format" {
    deviate not-supported;
  }
  deviation "/devm:devm/devm:cards/devm:card/pic:em-set" {
    deviate not-supported;
  }
  deviation "/devm:devm/devm:cards/devm:card/pic:service-switch" {
    deviate not-supported;
  }
  deviation "/devm:devm/devm:mpu-boards/devm:mpu-board/pic:cmac-padding" {
    deviate not-supported;
  }
  deviation "/devm:devm/devm:lpu-boards/devm:lpu-board/pic:cmac-padding" {
    deviate not-supported;
  }
  deviation "/devm:devm/devm:cards/devm:card/pic:cmu-switchs" {
    deviate not-supported;
  }
  deviation "/pic:pic/pic:auto-clears/pic:auto-clear/pic:type" {
    deviate replace {
      type pic-devs-OC-NE-X8X16:auto-clear-deviations;
    }
  }
  ext:deviation-ext "/pic:pic/pic:auto-clears/pic:auto-clear/pic:time" {
    ext:deviate-ext replace {
      ext:dynamic-default {
        ext:default-value "20" {
          when "../type = 'physical-mode'";
          description "The default value is 20 when type is physical-mode.";
        }
      }
    }
  }
  deviation "/pic:pic/pic:alarm-ais-inserts/pic:alarm-ais-insert/pic:name" {
    deviate replace {
      type pic-devs-OC-NE-X8X16:alarm-ais-insert-name-deviations;
    }
  }
  deviation "/pic:pic/pic:alarm-ais-inserts/pic:alarm-ais-insert/pic:ais" {
    deviate add {
      must "(../name = 'lpuneq' and ../ais = 'false') or (../name = 'hptim' or ../name = 'lptim' or ../name = 'rstim' or ../name = 'hpuneq' or ../name = 'hpplm')";
    }
  }
  deviation "/pic:pic/pic:alarm-ais-inserts/pic:alarm-ais-insert/pic:rdi" {
    deviate add {
      must "((../name = 'rstim' or ../name = 'hpuneq' or ../name = 'hpplm') and ../rdi = 'false') or (../name = 'hptim' or ../name = 'lptim' or ../name = 'lpuneq')";
    }
  }
  ext:deviation-ext "/pic:pic/pic:alarm-ais-inserts/pic:alarm-ais-insert/pic:rdi" {
    ext:deviate-ext add {
      ext:dynamic-default {
        ext:default-value "false" {
          when "../name = 'hpuneq' or ../name = 'hpplm' or ../name = 'lpuneq' or ../name = 'hptim' or ../name = 'lptim' or ../name = 'rstim'";
          description "The default value is false when name is hpuneq or hpplm or lpuneq or hptim or lptim or rstim.";
        }
      }
    }
  }
  deviation "/devm:devm/devm:ports/devm:port/pic:ethernet/pic:speed" {
    deviate replace {
      type pic-devs-OC-NE-X8X16:eth-speed-type-deviations;
    }
  }
  deviation "/devm:devm/devm:ports/devm:port/pic:ethernet/pic:negotiation-mode" {
    deviate replace {
      type pic-devs-OC-NE-X8X16:port-negotiation-mode-type-deviations;
    }
  }
  deviation "/devm:devm/devm:ports/devm:port/pic:cpos/pic:e1t1s/pic:e1t1/pic:work-mode" {
    deviate delete {
      default "framed";
    }
  }
  ext:deviation-ext "/devm:devm/devm:ports/devm:port/pic:cpos/pic:e1t1s/pic:e1t1/pic:work-mode" {
    ext:deviate-ext add {
      ext:dynamic-default;
    }
  }
  deviation "/devm:devm/devm:ports/devm:port/pic:cpos/pic:e1t1s/pic:e1t1/pic:clock-recovery-domain" {
    deviate add {
      must "((../clock='domain') and not(not(../clock-recovery-domain) and not(../clock-master-domain))) or (../clock='master') or (../clock='slave')";
    }
  }
  deviation "/devm:devm/devm:ports/devm:port/pic:cpos/pic:e1t1s/pic:e1t1/pic:clock-master-domain" {
    deviate add {
      must "((../clock='domain') and not(not(../clock-recovery-domain) and not(../clock-master-domain))) or (../clock='master') or (../clock='slave')";
    }
  }
  deviation "/devm:devm/devm:ports/devm:port/pic:cpos/pic:e1t1s/pic:e1t1/pic:loopback" {
    deviate add {
      must "((../clock='master' or ../clock='domain') and (../loopback='none' or ../loopback='local')) or (../clock='slave' and (../loopback='none' or ../loopback='remote'))";
    }
  }
  deviation "/devm:devm/devm:ports/devm:port/pic:cpos/pic:e1t1s/pic:e1t1/pic:channel-sets/pic:channel-set/pic:timeslot-list" {
    deviate replace {
      type string {
        length "1..85";
        pattern '((3[0-1]|[1-2][0-9]|[0-9])(-(3[0-1]|[1-2][0-9]|[1-9]))?(,((3[0-1]|[1-2][0-9]|[0-9])(-(3[0-1]|[1-2][0-9]|[1-9]))?))*)';
      }
    }
  }
  deviation "/devm:devm/devm:ports/devm:port/pic:port-alarm/pic:alarm-type/pic:crc-error-threshold/pic:crc-error-threshold/pic:crc-error-interval" {
    deviate add {
      must "not(../crc-error-percent-alm-thr)";
    }
  }
  deviation "/devm:devm/devm:ports/devm:port/pic:port-alarm/pic:alarm-type/pic:link-crc/pic:crc-per-alarm/pic:crc-per-alm-thr-power" {
    deviate replace {
      type uint32 {
        range "1..5";
      }
    }
  }
  deviation "/devm:devm/devm:ports/devm:port/pic:port-alarm/pic:alarm-type/pic:link-crc/pic:crc-per-alarm/pic:crc-per-rsum-thr-power" {
    deviate replace {
      type uint32 {
        range "1..6";
      }
    }
  }
  deviation "/devm:devm/devm:ports/devm:port/pic:e1t1/pic:channel-sets/pic:channel-set/pic:timeslot-list" {
    deviate replace {
      type string {
        length "1..85";
        pattern '((3[0-1]|[1-2][0-9]|[0-9])(-(3[0-1]|[1-2][0-9]|[1-9]))?(,((3[0-1]|[1-2][0-9]|[0-9])(-(3[0-1]|[1-2][0-9]|[1-9]))?))*)';
      }
    }
  }
  deviation "/devm:devm/devm:cards/devm:card/pic:service-mode/pic:bandwidth-mode" {
    deviate replace {
      type pic-devs-OC-NE-X8X16:card-service-mode-deviations;
    }
  }
  deviation "/devm:devm/devm:cards/devm:card/pic:port-group-modes/pic:port-group-mode/pic:mode-type" {
    deviate replace {
      type pic-devs-OC-NE-X8X16:card-port-group-mode-type-deviations;
    }
  }

}
