/******************************************************
* Copyright (C) 2021-2022 Huawei Technologies Co., Ltd. All rights reserved.
*******************************************************/
module huawei-cgn-common {
  namespace "urn:huawei:yang:huawei-cgn-common";
  prefix cgn-common;
  import huawei-extension {
    prefix ext;
  }
  import ietf-inet-types {
    prefix inet;
  }
  import huawei-network-instance {
    prefix ni;
  }
  import huawei-l3vpn {
    prefix l3vpn;
  }
  organization
    "Huawei Technologies Co., Ltd.";

  contact
    "Huawei Industrial Base
    Bantian, Longgang
    Shenzhen 518129
    People's Republic of China
    Website: http://www.huawei.com
    Email: support@huawei.com";

  description
    "This module contains a collection of YANG definitions for Configurations of cgn commaon element.";

  revision 2022-02-11 {
    description
      "Modify session-log-send-mode description.";
    reference
      "Huawei private.";
  }
  revision 2022-01-29 {
    description
      "Add grouping log-host and session-log-send-mode.";
    reference
      "Huawei private.";
  }
  revision 2021-11-05 {
    description
      "Add grouping port-range-set.";
    reference
      "Huawei private.";
  }
  revision 2021-07-31 {
    description
      "Initial revision.";
    reference
      "Huawei private.";
  }
  typedef alg-protocol-type {
    type enumeration {
      enum "ftp" {
          value 1;
          description "Indicate file transfer protocol.";
      }
      enum "rtsp" {
          value 2;
          description "Indicate real time streaming protocol.";
      }
      enum "pptp" {
          value 4;
          description "Indicate point-to-point tunnel protocol.";
      }
      enum "sip" {
          value 8;
          description "Indicate session initiation protocol.";
      }
      enum "dns" {
          value 16;
          description "Indicate domain name service.";
      }
    }
    description
      "ALG Protocol.";
  }

  grouping alg {
    description "Application level gateway.";
    container algs {
      description "List of Application level gateway.";
      list alg {
        key "protocol";
        description "Configure application level gateway.";
        leaf protocol {
          type alg-protocol-type;
          description "Protocol.";
        }
        leaf rate-threshold {
          when "../protocol='ftp'";
          type uint16 {
            range "64..15000";
          }
          units "pps";
          description
            "Enables NAT ALG rate limiting for standard FTP protocols.";
        }
        leaf separate-translation {
          when "../protocol='sip'";
          type boolean;
          default "false";
          description
            "Enable/disable the SIP control channel and data channel match an address-based NAT server separately in the NAT instance for NAT.";
        }
      }
    }
  }
  grouping port-range-set {
    description
      "NAT port-range initial and extend.";
    leaf initial-number {
      type uint16 {
        range "64..64512";
      }
      must "(../initial-number) mod 64 = 0";
      mandatory true;
      description
        "Port-range initial number, the value must be a multiple of 64.";
    }
    leaf extended-number {
      type uint16 {
        range "64..8192";
      }
      must "(../extended-number) mod 64 = 0";
      description
        "Port-range extended number, the value must be a multiple of 64.";
    }
    leaf extended-times {
      when ../extended-number;
      type uint8 {
        range "1..3";
      }
      must "(../initial-number + ../extended-number * ../extended-times) <= 64512";
      mandatory true;
      description
        "Specifies the number of extended port allocation times supported by the device.";
    }
  }
  grouping session-log-send-mode {
    description
      "Configure session log send mode is concurrent or polling.";
    leaf mode {
      type enumeration {
        enum "polling" {
        value 0;
        description
          "Polling-Mode.";
        }
        enum "concurrent" {
          value 1;
          description
            "Concurrent-Mode.";
        }
      }
      default "polling";
      description
        "Specify session log send mode.";
    }
  }
  grouping log-host {
    description "Configure log host.";
    container hosts {
      description "List of host.";
      list host {
        key "host-ip host-port vpn-name";
        description "Configure a log host.";
        leaf  host-ip {
          type inet:ipv4-address-no-zone;
          description "Specifies IP address of a log host.";
        }
        leaf host-port {
          type uint16 {
            range "1..65535";
          }
          description "Specifies the port number of a log host.";
        }
        leaf vpn-name {
          type leafref {
            path "/ni:network-instance/ni:instances/ni:instance/ni:name";
          }
          must "/ni:network-instance/ni:instances/ni:instance[ni:name=current()]/l3vpn:afs/l3vpn:af[l3vpn:type='ipv4-unicast']";
          description
            "Specifiy the name of VPN instance of the log host, the name of public network is _public_.";
        }
        leaf source-ip {
          type inet:ipv4-address-no-zone;
          mandatory true;
          description "Specifies the source IP address used by a device to communicate with a log host.";
        }
        leaf source-port {
          type uint16 {
            range "1..65535";
          }
          mandatory true;
          description "Specifies the source port number used by a device to communicate with a log host.";
        }
        leaf inside-vpn-name {
          type leafref {
            path "/ni:network-instance/ni:instances/ni:instance/ni:name";
          }
          must "/ni:network-instance/ni:instances/ni:instance[ni:name=current()]/l3vpn:afs/l3vpn:af[l3vpn:type='ipv4-unicast']";
          description
            "Specify the name of VPN instance on the private network side, the name of public network is _public_.";
        }
        leaf host-name {
          type string {
            length "1..31";
          }
          description "Specifies the name of a log host.";
        }
        leaf secondary {
          type boolean;
          default "false";
          description
            "Enable/disable the secondary log host group.";
        }
      }
    }
  }
  ext:task-name "nat";
}
