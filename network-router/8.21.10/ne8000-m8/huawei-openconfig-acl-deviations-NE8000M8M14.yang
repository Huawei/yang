/*
Copyright (C) 2021 Huawei Technologies Co., Ltd. All rights reserved.
*/
module huawei-openconfig-acl-deviations-NE8000M8M14 {
  namespace "urn:huawei:yang:huawei-openconfig-acl-deviations-NE8000M8M14";
  prefix oc-acl-devs-NE8000M8M14;

  import openconfig-acl {
    prefix oc-acl;
  }

  organization
    "Huawei Technologies Co., Ltd.";
  contact
    "Huawei Industrial Base
     Bantian, Longgang
     Shenzhen 518129
     People's Republic of China
     Website: http://www.huawei.com
     Email: support@huawei.com";
  description
    "This module defines deviation statements for openconfig-acl module.";

  revision 2021-05-07 {
    description
      "Initial revision.";
    reference "Huawei private.";
  }

  deviation "/oc-acl:acl" {
    deviate not-supported;
  }
}
