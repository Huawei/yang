/*
Copyright (C) 2021 Huawei Technologies Co., Ltd. All rights reserved.
*/
module huawei-pki-deviations-NE8000M8M14 {
  namespace "urn:huawei:yang:huawei-pki-deviations-NE8000M8M14";
  prefix pki-devs-NE8000M8M14;

  import huawei-pki {
    prefix pki;
  }

  organization
    "Huawei Technologies Co., Ltd.";
  contact
    "Huawei Industrial Base
     Bantian, Longgang
     Shenzhen 518129
     People's Republic of China
     Website: http://www.huawei.com
     Email: support@huawei.com";
  description
    "This module defines deviation statements for huawei-pki module.";

  revision 2021-05-07 {
    description
      "Initial revision.";
    reference "Huawei private.";
  }

  deviation "/pki:certificate-import" {
    deviate not-supported;
  }
  deviation "/pki:certificate-delete" {
    deviate not-supported;
  }
}
