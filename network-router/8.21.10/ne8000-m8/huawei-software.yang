/*
Copyright (C) 2019-2022 Huawei Technologies Co., Ltd. All rights reserved.
module: huawei-software
   +--rw software
      +--rw global
      |  +--rw auto-save
      |     +--rw enable?   boolean
      x--ro versions
      |  +--ro version* [base]
      |     +--ro base     string
      |     +--ro patch?   string
      +--ro startup-packages
      |  +--ro startup-package* [slot-id]
      |     +--ro slot-id            string
      |     +--ro current-package?   string
      |     +--ro next-package?      string
      +--ro packages
      |  +--ro package* [name]
      |     +--ro name            string
      |     +--ro package-type?   package-type
      +--ro upgrade-rollback-timer
      |  +--ro timer-enable?   boolean
      |  +--ro time?           uint32
      +--ro checkpoint-infos
      |  +--ro checkpoint-info* [name]
      |     +--ro name               string
      |     +--ro create-time?       yang:date-and-time
      |     +--ro create-mode?       checkpoint-create-type
      |     +--ro base-package?      string
      |     +--ro feature-package?   string
      |     +--ro patch-package?     string
      |     +--ro module-package?    string
      +--ro operation-schedules
         +--ro operation-schedule* [operation-type file-name]
            +--ro operation-type      operation-type
            +--ro file-name           string
            +--ro status?             operation-status
            +--ro fail-reason?        uint32
rpcs:
   +---x startup-by-mode
   |  +---w input
   |     +---w name    string
   |     +---w mode?   startup-mode
   +---x startup-by-slot-id
   |  +---w input
   |     +---w name       string
   |     +---w slot-id?   string
   +---x enable-upgrade-rollback
   |  +---w input
   |     +---w rollback-time    uint32
   +---x undo-upgrade-rollback
   +---x install-feature-software
   |  +---w input
   |     +---w name    string
   +---x uninstall-feature-software
   |  +---w input
   |     +---w name    string
   +---x upgrade-feature-software
   |  +---w input
   |     +---w name    string
   +---x startup-feature-software
   |  +---w input
   |     +---w feature-package-name    string
   +---x reset-feature-software-next-startup
   |  +---w input
   |     +---w feature-package-name    string
   +---x create-startup-checkpoint
   |  +---w input
   |     +---w name    -> /software/checkpoint-infos/checkpoint-info/name
   +---x delete-startup-checkpoint
   |  +---w input
   |     +---w name    -> /software/checkpoint-infos/checkpoint-info/name
   +---x check-startup-checkpoint
   |  +---w input
   |     +---w name    -> /software/checkpoint-infos/checkpoint-info/name
   +---x restore-startup-checkpoint
   |  +---w input
   |     +---w name    -> /software/checkpoint-infos/checkpoint-info/name
   +---x refresh-startup-secure-version-configuration
      +---w input
         +---w slot?   string
*/

module huawei-software {
  namespace "urn:huawei:yang:huawei-software";
  prefix software;

  import huawei-extension {
    prefix ext;
  }
  import ietf-yang-types {
    prefix yang;
  } 
  import ietf-inet-types {
    prefix inet;
  }
  import huawei-pub-type {
    prefix pub-type;
  }

  organization
    "Huawei Technologies Co., Ltd.";
  contact
    "Huawei Industrial Base
     Bantian, Longgang
     Shenzhen 518129
     People's Republic of China
     Website: http://www.huawei.com
     Email: support@huawei.com";
  description
    "Specify software package upgrade management.";
  revision 2022-03-31 {
    description
      "Delete base-version and patch-version from the key of upgrade-rollback-versions.";
    reference
      "Huawei private.";
  }
  revision 2022-03-02 {
    description
      "Correct misspelled words.";
    reference
      "Huawei private.";
  }
  revision 2022-02-08 {
    description
      "Add enum fail to type status-type.";
    reference
      "Huawei private.";
  }
  revision 2022-01-21 {
    description
      "Add import module ietf-inet-types, huawei-pub-type. Add type upgrade-rollback-type, upgrade-package-type, upgrade-version-type, version-status-type, upgrade-object-type, reboot-mode-type, transfer-protocol-type, action-type, status-type. Add container upgrade-rollback-versions, upgrade-package-infos, upgrade-action-results. Add rpc download-upgrade-package, load-upgrade-package, activate-upgrade-package, rollback-upgrade-package, delete-upgrade-package.";
    reference
      "Huawei private.";
  }
  revision 2021-09-24 {
    description
      "Add noderef to rpc enable-upgrade-rollback.";
    reference
      "Huawei private.";
  }
  revision 2021-07-30 {
    description
      "Modify the description of leaf feature-names.";
    reference
      "Huawei private.";
  }
  revision 2021-07-27 {
    description
      "Add rpc install-extended-system-software, uninstall-extended-system-software, startup-extended-system-software, reset-extended-system-software-next-startup, upgrade-extended-system-software.";
    reference
      "Huawei rpc .";
  }
  revision 2021-07-10 {
    description
      "Add rpc rollback-feature-software.";
    reference
      "Huawei private.";
  }
  revision 2021-04-30 {
    description
      "Add rpc in-service-upgrade-feature-software. Modify length and description of leaf name in rpc install-feature-software, uninstall-feature-software, upgrade-feature-software, startup-feature-software and reset-feature-software-next-startup.";
    reference
      "Huawei private.";
  }
  revision 2021-04-28 {
    description
      "Modify software-integrated-infos to integrated-infos.";
    reference
      "Huawei private.";
  }
  revision 2021-04-27 {
    description
      "Add startup-features.";
    reference
      "Huawei private.";
  }
  revision 2021-04-07 {
    description
      "Add software-integrated-infos.";
    reference
      "Huawei private.";
  }
  revision 2021-03-24 {
    description
      "Modify operation-schedules fail-reason type.";
    reference
      "Huawei private.";
  }
  revision 2021-03-11 {
    description
      "Add leaf software-name to packages.";
    reference
      "Huawei private.";
  }
  revision 2021-03-10 {
    description
      "Add integrate-software-package,restore-software-package,leaf-list current-feature-packages of startup-packages,leaf-list next-feature-packages of startup-packages.";
    reference
      "Huawei private.";
  }
  revision 2021-02-23 {
    description
      "Delete trust-startup-softwares.";
    reference
      "Huawei private.";
  }
  revision 2021-02-20 {
    description
      "Add trust-startup-softwares.";
    reference
      "Huawei private.";
  }
  revision 2021-02-04 {
    description
      "Add operation-schedules.";
    reference
      "Huawei private.";
  }
  revision 2020-12-31 {
    description
      "Add rpc reset-feature-software-next-startup.";
    reference
      "Huawei private.";
  }
  revision 2020-06-30 {
    description
      "Revert modification of software node's config attribute.";
    reference
      "Huawei private.";
  }
  revision 2020-06-29 {
    description
      "Modify node description.";
    reference
      "Huawei private.";
  }
  revision 2020-05-27 {
    description
      "Add rpc refresh-startup-secure-version-configuration.";
    reference
      "Huawei private.";
  }
  revision 2020-03-02 {
    description
      "Add install-feature-software, uninstall-feature-software, upgrade-feature-software.";
    reference
      "Huawei private.";
  }
  revision 2019-12-02 {
    description
      "Initial revision.";
    reference
      "Huawei private.";
  }
  ext:task-name "upgrade";
  typedef startup-mode {
    type enumeration {
      enum "primary" {
        value 1;
        description
          "Upgrade the software package on the master MPU.";
      }
      enum "slave" {
        value 2;
        description
          "Upgrade the software package on the slave MPU.";
      }
      enum "all" {
        value 3;
        description
          "Upgrade the software package on all MPUs.";
      }
    }
    description
      "Startup mode.";
  }
  typedef package-type {
    type enumeration {
      enum "system" {
        value 1;
        description
          "The type of a software package on the device is a system software package.";
      }
      enum "feature" {
        value 2;
        description
          "The type of a software package on the device is a feature software package.";
      }
      enum "system-extended" {
        value 3;
        description
          "The type of a software package on the device is a extended system software package.";
      }
    }
    description
      "Specify the type of a software package on the device.";
  }
  typedef checkpoint-create-type {
    type enumeration {
      enum "manual" {
        value 1;
        description
          "The type of a checkpoint created mode.";
      }
      enum "auto" {
        value 2;
        description
          "The type of a checkpoint created mode.";
      }
    }
    description
      "Specify the type of a software package on the device.";
  }
  typedef operation-type {
    type enumeration {
      enum "startup-system-software" {
        value 0;
        description
          "Startup the system software.";
      }
      enum "install-feature-software" {
        value 1;
        description
          "Install the feature software.";
      }
      enum "uninstall-feature-software" {
        value 2;
        description
          "Uninstall the feature software.";
      }
      enum "upgrade-feature-software" {
        value 3;
        description
          "Upgrade the feature software.";
      }
      enum "startup-feature-software" {
        value 4;
        description
          "Startup the feature software.";
      }
      enum "reset-feature-software" {
        value 5;
        description
          "Reset the feature software.";
      }
      enum "install-extended-system-software" {
        value 6;
        description
          "Install the extended system software.";
      }
      enum "uninstall-extended-system-software" {
        value 7;
        description
          "Uninstall the extended system software.";
      }
      enum "upgrade-extended-system-software" {
        value 8;
        description
          "Upgrade the extended system software.";
      }
      enum "startup-extended-system-software" {
        value 9;
        description
          "Startup the extended system software.";
      }
      enum "reset-next-startup-extended-system-software" {
        value 10;
        description
          "Reset the next startup extended system software.";
      }
    }
    description
      "Specify the operation type of software.";
  }
  typedef operation-status { 
    type enumeration {
      enum "not-started" {
        value 0;
        description
          "The current status is not started.";
      }
      enum "operating" {
        value 1;
        description
          "The current status is operating.";
      }
      enum "successful" {
        value 2;
        description
          "The current status is successful.";
      }
      enum "failed" {
        value 3;
        description
          "The current status is failed.";
      }
    }
    description
      "Specify the operation status of software.";
  }
  typedef operation-fail-reason { 
    type enumeration {
      enum "para-invalid" {
        value 0;
        description
          "Para is invalid.";
      }
      enum "system-busy" {
        value 1;
        description
          "Another user is performing package management opertions.";
      }
      enum "integrity-check-failed" {
        value 2;
        description
          "Integrity check failed.";
      }
      enum "compatibility-check-failed" {
        value 3;
        description
          "Compatibility check failed.";
      }
      enum "dependency-check-failed" {
        value 4;
        description
          "Dependency check failed.";
      }
      enum "version-revoked" {
        value 5;
        description
          "Version revoked.";
      }
      enum "startup-error" {
        value 6;
        description
          "Startup error.";
      }
      enum "install-error" {
        value 7;
        description
          "Install error.";
      }
      enum "uninstall-error" {
        value 8;
        description
          "Uninstall error.";
      }
      enum "upgrade-error" {
        value 9;
        description
          "Upgrade error.";
      }
      enum "reset-error" {
        value 10;
        description
          "Reset error.";
      }
    }
    description
      "Specify software operation fail reason.";
  }
  typedef feature-status { 
    type enumeration {
      enum "inactive" {
        value 0;
        description
          "Feature package was not activated.";
      }
      enum "active" {
        value 1;
        description
          "Feature package was activated.";
      }
    }
    description
      "Specify the feature package was activated or deactivated.";
  }
  typedef upgrade-rollback-type {
    type enumeration {
      enum "last" {
        value 0;
        description
          "Rollback to the last base software and patch.";
      }
      enum "base-software" {
        value 1;
        description
          "Rollback the base software.";
      }
      enum "patch" {
        value 2;
        description
          "Rollback the patch.";
      }
    }
    description
      "Upgrade rollback type.";
  }
  typedef upgrade-package-type {
    type enumeration {
      enum "base-software-package" {
        value 0;
        description
          "Base software package.";
      }
      enum "risk-check-package" {
        value 1;
        description
          "Risk check package.";
      }
      enum "application-package" {
        value 2;
        description
          "Application package.";
      }
    }
    description
      "Upgrade package type.";
  }
  typedef upgrade-version-type {
    type enumeration {
      enum "base-software" {
        value 0;
        description
          "Base software.";
      }
      enum "cold-patch" {
        value 1;
        description
          "Cold patch.";
      }
      enum "hot-patch" {
        value 2;
        description
          "Hot patch.";
      }
    }
    description
      "Upgrade version type.";
  }
  typedef version-status-type {
    type enumeration {
      enum "ready" {
        value 0;
        description
          "The package is ready for loading.";
      }
      enum "prepared" {
        value 1;
        description
          "The package has been loaded.";
      }
      enum "running" {
        value 2;
        description
          "The package is running.";
      }
      enum "running-and-prepared" {
        value 3;
        description
          "The package is running and has been loaded.";
      }
    }
    description
      "Version status type.";
  }
  typedef upgrade-object-type {
    type enumeration {
      enum "base-software" {
        value 0;
        description
          "Base software.";
      }
      enum "patch" {
        value 1;
        description
          "Patch.";
      }
      enum "all" {
        value 2;
        description
          "Base software and patch.";
      }
    }
    description
      "Upgrade object Type.";
  }
  typedef reboot-mode-type {
    type enumeration {
      enum "no-reboot" {
        value 0;
        description
          "No reboot.";
      }
      enum "soft-reboot" {
        value 1;
        description
          "Soft reboot.";
      }
    }
    description
      "Reboot mode type.";
  }
  typedef transfer-protocol-type {
    type enumeration {
      enum "sftp" {
        value 0;
        description
          "Secure file transfer protocol.";
      }
    }
    description
      "Type of the transfer protocol.";
  }
  typedef action-type {
    type enumeration {
      enum "download-package" {
        value 0;
        description
          "Download package.";
      }
      enum "load-package" {
        value 1;
        description
          "Load package.";
      }
      enum "activate-package" {
        value 2;
        description
          "Activate package.";
      }
      enum "rollback-package" {
        value 3;
        description
          "Rollback package.";
      }
      enum "delete-package" {
        value 4;
        description
          "Delete package.";
      }
      enum "none" {
        value 99;
        description
          "Nothing to do.";
      }
    }
    description
      "Action type.";
  }
  typedef status-type {
    type enumeration {
      enum "end" {
        value 0;
        description
          "End.";
      }
      enum "doing" {
        value 1;
        description
          "Doing.";
      }
      enum "start" {
        value 2;
        description
          "Start.";
      }
      enum "fail" {
        value 3;
        description
          "Fail.";
      }
    }
    description
      "Status type.";
  }
  container software {
    description
      "Specify software package upgrade management.";
    container global {
      description "Configure of auto save checkpoint switch.";
      container auto-save {
        description "Configure of enable auto save checkpoint.";
	leaf enable {
	  type boolean;
	  default "true";
	  description "Enable/disable auto save checkpoint when upgrade software package.";    
	}
      }
    }
    container versions {
      config false;
      status deprecated;
      description
        "List of operational state of software package versions. The node versions is deprecated. You are advised to use the node /system/system-info.";
      list version {
        key "base";
        status deprecated;
        description
          "Operational state of a software package version. The node version is deprecated. You are advised to use the node /system/system-info.";
        leaf base {
          type string {
            length "1..63";
          }
          status deprecated;
          description
            "Current software package version. The node base is deprecated. You are advised to use the node /system/system-info/product-version.";
        }
        leaf patch {
          type string {
            length "1..63";
          }
          status deprecated;
          description
            "Current patch package version. The node patch is deprecated. You are advised to use the node /system/system-info/patch-version.";
        }
      }
    }
    container startup-packages {
      config false;
      description
        "List of operational state of startup software packages.";
      list startup-package {
        key "slot-id";
        description
          "Operational state of startup software package.";
        leaf slot-id {
          type string {
            length "1..31";
          }
          description
            "Slot ID.";
        }
        leaf current-package {
          type string {
            length "4..255";
          }
          description
            "The name of a software package used at the current startup.";
        }
        leaf next-package {
          type string {
            length "4..255";
          }
          description
            "The name of a software package used at the next startup.";
        }
        leaf-list current-feature-packages {
          type string {
            length "4..255";
          }
          description
            "Operational data of the feature software packages used at the current startup. Name of the files that end with ccx.";
        }
        leaf-list next-feature-packages {
          type string {
            length "4..255";
          }
          description
            "Operational data of the feature software packages used at the next startup. Name of the files that end with ccx.";
        }
        leaf-list current-extended-system-packages {
          type string {
            length "5..255";
          }
          description
            "Operational data of the extended system software packages used at the current startup. Name of the files that end with cch.";
        }
        leaf-list next-extended-system-packages {
          type string {
            length "5..255";
          }
          description
            "Operational data of the extended system software packages used at the next startup. Name of the files that end with cch.";
        }
      }
    }
    container packages {
      config false;
      description
        "List of operational state of software packages on the device.";
      list package {
        key "name";
        description
          "Operational state of a software package on the device.";
        leaf name {
          type string {
            length "4..255";
          }
          description
            "The file name of a software package on the device, which can be modified by users.";
        }
        leaf software-name {
          type string {
            length "4..255";
          }
          description
            "The software name of the software package file, which is published with package and can not be modified.";
        }
        leaf package-type {
          type package-type;
          description
            "The type of a software package on the device.";
        }
        leaf version {
          type string {
            length "1..63";
          }
          description
            "Specify the version of a feature software package.";
        }
        leaf-list feature-names {
          type string {
            length "1..127";
          }
          description
            "Operational data of the feature package name of a software package.";
        }
      }
    }
    container upgrade-rollback-timer {
      config false;
	  description
        "Operational data of upgrade rollback timer.";
      leaf timer-enable {
        type boolean;
        description
          "When the rollback timer is closed, the time leaf will not be shown.";
      }
      leaf time {
        when "../timer-enable = 'true'";
        type uint32 {
          range "10..360";
        }
        units min;
        description
          "Rollback time.";
      }
    }
    container checkpoint-infos {
      config false;
      description "List of checkpoint base information.";
      list checkpoint-info {
        key "name";
        description 
	  "Statistics of a checkpoint info.";
        leaf name {
          type string {
            length "5..32";
          }
          description "Checkpoint name.";    
        }
        leaf create-time {
          type yang:date-and-time;
          description "Checkpoint create time.";
        }
        leaf create-mode {
          type checkpoint-create-type;
          description "Checkpoint create mode.";
        }
        leaf base-package {
          type string {
            length "0..255";
          }
          description "Checkpoint software package.";
        }
        leaf feature-package {
          type string {
            length "0..2047";
          }
          description "Checkpoint feature packages.";
        }
        leaf patch-package {
          type string {
            length "0..2047";
          }
          description "Checkpoint patch packages.";
        }
        leaf module-package {
          type string {
            length "0..2047";
          }
          description "Checkpoint module patches.";
        }
        leaf paf-file {
          type string {
            length "0..255";
          }
          description "Checkpoint PAF file.";
        }
        leaf saved-configuration-file {
          type string {
            length "0..255";
          }
          description "Checkpoint saved-configuration file.";
        }
        leaf-list extended-packages {
          type string {
            length "5..255";
          }
          description "Operational data of the extended system software packages. Name of the files that end with cch.";
        }
      }
    }
    container operation-schedules {
      config false;
      description
        "List of operational state of software packages.";
      list operation-schedule {
        key "operation-type";
        description
          "Operational state of software packages.";
        leaf operation-type {
          type operation-type;
          description
            "Software operation type.";
        }
        leaf file-name {
          type string {
            length "5..63";
          }
          description
            "Software package name.";
        }
        leaf status {
          type operation-status;
          description
            "Status of the software operation.";
        }
        leaf fail-reason {
          when "../status = 'failed'";
          type operation-fail-reason;
          description
            "Cause of the software operation failure.";
        }
      }
    }
    container integrated-infos {
      config false;
      description
        "List of software packages on the device.";
      list integrated-info {
        key "name";
        description
          "Operational data of a software package on the device."; 
        leaf name {
          type string {
            length "4..127";
          }
          description
            "Specify the name of a software package on the device.";
        }
        leaf package-integrated-version {
          type string {
            length "1..63";
          }
          description
            "Specify the integrated version of a software package on the device.";
        }
        leaf component-status {
          type string {
            length "1..63";
          }
          description
            "Specify the component status of a software package on the device.";
        }
        leaf component-version {
          type string {
            length "1..63";
          }
          description
            "Specify the component version of a software package on the device.";
        }
      }
    }
    container startup-features {
        config false;
        description
            "List of startup feature software package versions.";

        list startup-feature {
            key "feature-name location";
            
            description
                "Operational data of a startup feature software package version information.";
            
            leaf feature-name {
                type string {
                    length "1..63";
                }
                description
                "Specify the feature name of a feature software package used at the current startup.";
            }
            leaf location {
                type string {
                    length "5..255";
                }
                description
                "Specify the file name of a feature software package used at the current startup.";
            }
            leaf status {
                type feature-status;
                description
                    "Specify the feature package is active or inactive.";
            }
            leaf version {
                type string {
                    length "1..63";
                }
                description
                    "Specify the software version of a feature software package used at the current startup.";
            }
            leaf activated-time {
                type yang:date-and-time;
                description
                    "Specify the software installation time of a feature software package used at the current startup.";
            }
        }
    }
    container upgrade-rollback-versions {
      config false;
      description
        "List of the upgrade rollback version.";
      list upgrade-rollback-version {
        key "rollback-type";
        description
          "Operational data of the upgrade rollback version.";
        leaf rollback-type {
          type upgrade-rollback-type;
          description
            "Rollback type.";
        }
        leaf base-version {
          type string {
            length "1..31";
          }
          description
            "Rollback base software package version.";
        }
        leaf patch-version {
          type string {
            length "1..31";
          }
          description
            "Rollback patch version.";
        }
      }
    }
    container upgrade-package-infos {
      config false;
      description
        "List of the upgrade package information.";
      list upgrade-package-info {
        key "package-type version-type version application-type version-status";
        description
          "Operational data of the upgrade package information.";
        leaf package-type {
          type upgrade-package-type;
          description
            "Type of the upgrade package.";
        }
        leaf version-type {
          type upgrade-version-type;
          description
            "Version type of the upgrade package.";
        }
        leaf version {
          type string {
            length "1..31";
          }
          description
            "Version of the upgrade package.";
        }
        leaf application-type {
          type string {
            length "1..63";
          }
          description
            "Application type of the upgrade package.";
        }
        leaf version-status {
          type version-status-type;
          description
            "Version status of the upgrade package.";
        }
      }
    }
    container upgrade-action-results {
      config false;
      description
        "List of the upgrade action results.";
      list upgrade-action-result {
        key "command";
        description
          "Operational data of the upgrade action results.";
        leaf command {
          type action-type;
          description
            "Command of the action.";
        }
        leaf action-start-time {
          type yang:date-and-time;
          description
            "Start time of the action.";
        }
        leaf action-end-time {
          type yang:date-and-time;
          description
            "End time of the action.";
        }
        leaf action-status {
          type status-type;
          description
            "Status of the action.";
        }
        leaf action-progress {
          type pub-type:percent;
          description
            "Progress of the action.";
        }
      }
    }
  }
  rpc startup-by-mode {
    description
      "Specify the mode-based upgrade for software packages.";
    ext:node-ref "/software/packages/package";  
    input {
      leaf name {
        type string {
          length "4..127";
        }
        mandatory true;
        description
          "Specify the name of a software package that needs to be upgraded.";
      }
      leaf mode {
        type startup-mode;
        description
          "Specify a software package upgrade mode.";
      }
    }
  }
  rpc startup-by-slot-id {
    description
      "Specify the slot ID-based upgrade for software packages.";
    ext:node-ref "/software/packages/package";
    input {
      leaf name {
        type string {
          length "4..127";
        }
        mandatory true;
        description
          "Specify the name of a software package that needs to be upgraded.";
      }
      leaf slot-id {
        type string {
          length "1..31";
        }
        description
          "Specify the slot ID of a board on which a software package needs to be upgraded.";
      }
    }
  }
  rpc enable-upgrade-rollback {
    ext:node-ref "/software/upgrade-rollback-timer";
    description
      "Specify the rollback time when upgrade software package.";
    input {
      leaf rollback-time {
        type uint32 {
          range "10..360";
        }
        units min;
        mandatory true;
        description
          "Specify the rollback time.";
      }
    }
  }
  rpc undo-upgrade-rollback {
    ext:node-ref "/software/upgrade-rollback-timer";
    description
      "Delete the rollback time when upgrade software package.";
  }
  rpc install-feature-software {
    description
      "Install feature software.";
    input  {
      leaf name {
        type string {
          length "1..127";
        }
        mandatory true;
        description
          "Specifies the name of feature software package. Two types are available. One type of feature software package ends with '.ccx'. The other type of feature software package is in the system software package without a suffix.";
      }
    }
  }
  rpc uninstall-feature-software {
    description
      "Uninstall feature software.";
    input  {
      leaf name {
        type string {
          length "1..127";
        }
        mandatory true;
        description
          "Specifies the name of feature software package. Two types are available. One type of feature software package ends with '.ccx'. The other type of feature software package is in the system software package without a suffix.";
      }
    }
  }
  rpc upgrade-feature-software {
    description
      "Upgrade feature software on line.";
    input  {
      leaf name {
        type string {
          length "1..127";
        }
        mandatory true;
        description
          "Specifies the name of feature software package. Two types are available. One type of feature software package ends with '.ccx'. The other type of feature software package is in the system software package without a suffix.";
      }
    }
  }
  rpc startup-feature-software {
    description
      "Startup feature software.";
    input  {
      leaf feature-package-name {
        type string {
          length "5..127";
        }
        mandatory true;
        description
          "Specify the name of an independent feature software package which ends with '.ccx'.";
      }
    }  
}
  rpc reset-feature-software-next-startup {
    description
      "Reset next startup feature software.";
    input  {
      leaf feature-package-name {
        type string {
          length "5..127";
        }
        mandatory true;
        description
          "Specify the name of an independent feature software package which ends with '.ccx'.";
      }
    }  
  }
  rpc create-startup-checkpoint {
    description
      "Create a specified startup checkpoint.";
    input  {
      leaf name {
        type string {
          length "5..32";
        }
	mandatory true;
        description
          "Specify the name of a checkpoint.";
      }
    }
  }
  rpc delete-startup-checkpoint {
    ext:node-ref "/software/checkpoint-infos/checkpoint-info";
    description
      "Delete a specified startup checkpoint.";
    input  {
      leaf name {
        type leafref {
          path "/software/checkpoint-infos/checkpoint-info/name";
        }
	mandatory true;
        description
          "Specify the name of a checkpoint.";
      }
    }
  }
  rpc check-startup-checkpoint {
    ext:node-ref "/software/checkpoint-infos/checkpoint-info";
    description
      "Check a specified startup checkpoint.";
    input  {
      leaf name {
        type leafref {
          path "/software/checkpoint-infos/checkpoint-info/name";
        }
	mandatory true;
        description
          "Specify the name of a checkpoint.";
      }
    }
  }
  rpc restore-startup-checkpoint {
    ext:node-ref "/software/checkpoint-infos/checkpoint-info";
    description
      "Restore a specified checkpoint.";
    input  {
      leaf name {
        type leafref {
          path "/software/checkpoint-infos/checkpoint-info/name";
        }
	mandatory true;
        description
          "Specify the name of a checkpoint.";
      }
    }
  }
  rpc refresh-startup-secure-version-configuration {
    description
      "Update the eFUSE and version revocation list. If the slot parameter is not specified, information on all boards is updated.";
    input {
      leaf slot {
        type string {
          length "1..49";
        }
        description
          "Specify the slot name.";
      }
    }
  }
  rpc integrate-software-package {
    description
      "Integrate software package.";
    input  {
      leaf original-package {
        type string {
          length "4..127";
        }
        mandatory true;
        description
          "Specify the name of a original software package.";
      }
      leaf integrated-package {
        type string {
          length "4..127";
        }
        mandatory true;
        description
          "Specify the name of a integrated software package.";
      }
      leaf signature-backup-file {
        type string {
          length "4..127";
        }
        mandatory true;
        description
          "Specify the name of the software package containing signature backup file.";
      }
    }
  }
  rpc restore-software-package {
    description
      "Restore software package.";
    input  {
      leaf integrated-package {
        type string {
          length "4..127";
        }
        mandatory true;
        description
          "Specify the name of a integrated software package.";
      }
      leaf signature-backup-file {
        type string {
          length "4..127";
        }
        mandatory true;
        description
          "Specify the name of the software package containing signature backup file.";
      }
    }
  }
  rpc in-service-upgrade-feature-software {
    description
      "Upgrade feature software in service.";
    input  {
      leaf name {
        type string {
          length "5..127";
        }
        mandatory true;
        description
          "Specify the name of an independent feature software package which ends with '.ccx'.";
      }
    }
  }
  rpc rollback-feature-software {
    description
      "Roll back the most recently upgraded feature software.";
  }
  rpc install-extended-system-software {
    description
      "Install extended system software.";
    input  {
      leaf name {
        type string {
          length "5..127";
        }
        mandatory true;
        description
          "Specifies the name of an extended system software package which ends with '.cch'.";
      }
    }
  }
  rpc uninstall-extended-system-software {
    description
      "Uninstall extended system software.";
    input  {
      leaf name {
        type string {
          length "5..127";
        }
        mandatory true;
        description
          "Specifies the name of an extended system software package which ends with '.cch'.";
      }
    }
  }
  rpc upgrade-extended-system-software {
    description
      "Upgrade extended system software on line.";
    input  {
      leaf name {
        type string {
          length "5..127";
        }
        mandatory true;
        description
          "Specifies the name of an extended system software package which ends with '.cch'.";
      }
    }
  }
  rpc startup-extended-system-software {
    description
      "Startup extended system software.";
    input  {
      leaf name {
        type string {
          length "5..127";
        }
        mandatory true;
        description
          "Specifies the name of an extended system software package which ends with '.cch'.";
      }
    }  
  }
  rpc reset-extended-system-software-next-startup {
    description
      "Reset next startup extended system software.";
    input  {
      leaf name {
        type string {
          length "5..127";
        }
        mandatory true;
        description
          "Specifies the name of an extended system software package which ends with '.cch'.";
      }
    }  
  }
  rpc download-upgrade-package {
    description
      "Download the package for upgrade.";
    input {
      leaf server-ip {
        type inet:ipv4-address-no-zone;
        mandatory true;
        description
          "Specify the IP address of the download server.";
      }
      leaf server-port {
        type uint32 {
          range "1..65535";
        }
        mandatory true;
        description
          "Specify the port number of the download server.";
      }
      leaf user-name {
        type string{
          length "1..63";
        }
        mandatory true;
        description
          "Specify the user name.";
      }
      leaf password {
        type pub-type:password {
            length "1..127";
        }
        mandatory true;
        description
          "Specify the password.";
      }
      leaf upgrade-object {
        type upgrade-object-type;
        mandatory true;
        description
          "Specify the upgrade object. For exapmle base software or patch.";
      }
      leaf base-software-directory {
        when "../upgrade-object = 'base-software' or ../upgrade-object = 'all'";
        type string{
          length "1..127";
        }
        mandatory true;
        description
          "Specify the directory of the base software package on the server.";
      }
      leaf patch-directory {
        when "../upgrade-object = 'patch' or ../upgrade-object = 'all'";
        type string{
          length "1..127";
        }
        mandatory true;
        description
          "Specify the directory of the patch package on the server.";
      }
      leaf transfer-protocol {
        type transfer-protocol-type;
        default "sftp";
        description
          "Specify the transfer protocol.";
      }
    }
  }
  rpc load-upgrade-package {
    description
      "Load the package for upgrade.";
    input {
      leaf upgrade-object {
        type upgrade-object-type;
        mandatory true;
        description
          "Specify the upgrade object.";
      }
      leaf base-version {
        when "../upgrade-object = 'base-software' or ../upgrade-object = 'all'";
        type string {
          length "1..31";
        }
        mandatory true;
        description
          "Specify the version of the base software to be loaded.";
      }
      leaf patch-version {
        when "../upgrade-object = 'patch' or ../upgrade-object = 'all'";
        type string {
          length "1..31";
        }
        mandatory true;
        description
          "Specify the version of the patch to be loaded.";
      }
    }
  }
  rpc activate-upgrade-package {
    description
      "Activate the package for upgrade.";
    input {
      leaf upgrade-object {
        type upgrade-object-type;
        mandatory true;
        description
          "Specify the upgrade object.";
      }
      leaf base-version {
        when "../upgrade-object = 'base-software' or ../upgrade-object = 'all'";
        type string {
          length "1..31";
        }
        mandatory true;
        description
          "Specify the version of the base software to be activated.";
      }
      leaf patch-version {
        when "../upgrade-object = 'patch' or ../upgrade-object = 'all'";
        type string {
          length "1..31";
        }
        mandatory true;
        description
          "Specify the version of the patch to be activated.";
      }
      leaf reboot-mode {
        type reboot-mode-type;
        default "no-reboot";
        description
          "Specify the reboot mode.";
      }
      leaf rollback-timer {
        type uint32;
        description
          "Specify the value of the rollback timer in minutes.";
      }
    }
  }
  rpc rollback-upgrade-package {
    description
      "Rollback the package for upgrade.";
    input {
      leaf upgrade-object {
        type upgrade-object-type;
        mandatory true;
        description
          "Specify the upgrade object.";
      }
      leaf rollback-type {
        type upgrade-rollback-type;
        mandatory true;
        description
          "Specify the rollback type.";
      }
      leaf base-version {
        when "../upgrade-object = 'base-software' or ../upgrade-object = 'all'";
        type string {
          length "1..31";
        }
        mandatory true;
        description
          "Specify the version of the base software for rollback.";
      }
      leaf patch-version {
        when "../upgrade-object = 'patch' or ../upgrade-object = 'all'";
        type string {
          length "1..31";
        }
        mandatory true;
        description
          "Specify the version of the patch for rollback.";
      }
      leaf reboot-mode {
        type reboot-mode-type;
        default "no-reboot";
        description
          "Specify the reboot mode.";
      }
    }
  }
  rpc delete-upgrade-package {
    description
      "Delete the package for upgrade.";
    input {
      leaf reboot-mode {
        type reboot-mode-type;
        default "no-reboot";
        description
          "Specify the reboot mode.";
      }
    }
  }
}
