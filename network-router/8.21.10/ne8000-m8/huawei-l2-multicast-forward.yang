/*
Copyright (C) 2019-2022 Huawei Technologies Co., Ltd. All rights reserved.
*/
module huawei-l2-multicast-forward {
  namespace urn:huawei:yang:huawei-l2-multicast-forward;
  prefix l2-multicast-forward;
  
  import huawei-vlan {
    prefix vlan;
  }
  import huawei-extension {
    prefix ext;
  } 
  import huawei-devm {
    prefix devm;
  } 
  import huawei-bd {
    prefix bd;
  } 
  import huawei-l2vpn {
    prefix l2vpn;
  }
  import huawei-igmp-mld-snooping {
    prefix ims;
  }
  import huawei-nvo3 {
    prefix nvo3;
  }
  organization
    "Huawei Technologies Co., Ltd.";
  contact
    "Huawei Industrial Base
     Bantian, Longgang
     Shenzhen 518129
     People's Republic of China
     Website: http://www.huawei.com
     Email: support@huawei.com";
  description
    "L2 multicast VLAN fwroding.";
  revision 2022-02-20 {
    description
      "Add trunk-load-balance nodes.";
    reference
      "Huawei private.";
  }
  revision 2019-07-01 {
    description
      "Init revision.";
    reference
      "Huawei private.";
  }
  ext:task-name "l2mc";
  typedef l2mc-forward-mode {
    type enumeration {
      enum "ip" {
	    value 1;
        description
          "Forwarding based on IP addresses.";
      }
      enum "mac" {
	    value 2;	  
        description
          "Forwarding based on MAC addresses.";
      }
    }
    description
      "Forwarding mode.";
  }
  typedef sg-type {
    type enumeration {
      enum "SG" {
        value 1;
        description
          "Multicast entry in which both group and source addresses are specified.";
      }
      enum "source-wildcard" {
        value 2;	  
        description
          "Multicast entry in which only a group address is specified.";
      }
      enum "rt-port" {
        value 3;	  
        description
          "Router port.";
      }
    }
    description
      "Port type.";
  } 
  container l2-multicast-forward {
    description
      "Global configuration of l2mc forward.";
    container select-boards {
      description
        "Configure boards selected for l2mc.";
      leaf-list slot {
        type leafref {
          path "/devm:devm/devm:lpu-boards/devm:lpu-board/devm:position";
        }
        max-elements "20";
        description
          "Configure slot ID.";
      }
    }
  }  
  augment "/vlan:vlan/vlan:vlans/vlan:vlan" {
    description
	  "Multicast forward configuration to the VLAN module.";
    container multicast-forward {
      description
        "Configure multicast-forward configurations in the VLAN.";
      container port-isolate-state {	  
        description
          "Configure the isolation of non-multicast traffic in a VLAN.";
        leaf enable {
          type boolean;
          default "false";
          description
            "Enable/disable isolate non-multicast traffic.";
        }
      }
      container trunk-load-balance-enable {
        must "../../vlan:type!='super'";
        must "../../ims:igmp-snooping/ims:global/ims:enable!='true'";
        must "../../ims:mld-snooping/ims:global/ims:enable!='true'";
        must "../../vlan:unknown-multicast-discard!='enable'";
        presence "Trunk load-balance enable";
        description
          "Enable/disable trunk load-balance configurations.";
      }
    }
  }
  augment "/l2vpn:l2vpn/l2vpn:instances/l2vpn:instance/l2vpn:vpls" {
    description
      "Multicast forward configuration to the L2VPN module."; 
    container multicast-forward {
      description
        "Configure multicast-forward configurations in the VSI.";
      container trunk-load-balance-enable {
        must "../../l2vpn:work-mode!='b-vsi' and ../../l2vpn:work-mode!='i-vsi' and ../../l2vpn:work-mode!='i-vsi-p2p' and ../../l2vpn:work-mode!='i-vsi-b-evpn-interworking'";
        must "../../ims:igmp-snooping/ims:global/ims:enable!='true'";
        must "../../ims:mld-snooping/ims:global/ims:enable!='true'";
        must "../../l2vpn:unknown-multicast-action!='drop'";
        presence "Trunk load-balance enable";
        description
          "Enable/disable trunk load-balance configurations.";
      }
    }
  }
  augment "/bd:bd/bd:instances/bd:instance" {
    description
      "Multicast forward configuration to the bd module."; 
    container multicast-forward {
      description
        "Configure multicast-forward configurations in the BD.";
      container trunk-load-balance-enable {
        must "../../ims:igmp-snooping/ims:global/ims:enable!='true'";
        must "not(../../nvo3:nvo3/nvo3:vni-list)";
        must "../../bd:unknown-unicast-discard!='enable'";
        presence "Trunk load-balance enable";
        description
          "Enable/disable trunk load-balance configurations.";
      }
    }
  }
}
