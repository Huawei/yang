/*
Copyright (C) 2021 Huawei Technologies Co., Ltd. All rights reserved.
*/
module huawei-wdm-deviations-NE8000M8M14 {
  namespace "urn:huawei:yang:huawei-wdm-deviations-NE8000M8M14";
  prefix wdm-devs-NE8000M8M14;

  import huawei-wdm {
    prefix wdm;
  }

  import huawei-driver {
    prefix driver;
  }

  import huawei-pic {
    prefix pic;
  }

  organization
    "Huawei Technologies Co., Ltd.";

  contact
    "Huawei Industrial Base
     Bantian, Longgang
     Shenzhen 518129
     People's Republic of China
     Website: http://www.huawei.com
     Email: support@huawei.com";

  description
    "This module defines deviation statements for huawei-wdm module.";

  revision 2021-05-07 {
    description
      "Initial revision.";
    reference
      "Huawei private.";
  }

  deviation "/driver:driver/driver:global-attribute/pic:global/wdm:source-pm-measurement" {
    deviate not-supported;
  }

}
