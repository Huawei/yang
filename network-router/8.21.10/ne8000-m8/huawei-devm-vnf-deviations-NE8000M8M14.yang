/*
Copyright (C) 2021 Huawei Technologies Co., Ltd. All rights reserved.
*/
module huawei-devm-vnf-deviations-NE8000M8M14 {
  namespace "urn:huawei:yang:huawei-devm-vnf-deviations-NE8000M8M14";
  prefix devm-vnf-devs-NE8000M8M14;

  import huawei-devm-vnf {
    prefix devm-vnf;
  }

  organization
    "Huawei Technologies Co., Ltd.";
  contact
    "Huawei Industrial Base
     Bantian, Longgang
     Shenzhen 518129
     People's Republic of China
     Website: http://www.huawei.com
     Email: support@huawei.com";
  description
    "This module defines deviation statements for huawei-devm-vnf module.";

  revision 2021-05-07 {
    description
      "Initial revision.";
    reference "Huawei private.";
  }

  deviation "/devm-vnf:devm-vnf" {
    deviate not-supported;
  }
}
