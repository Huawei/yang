/*
Copyright (C) 2021 Huawei Technologies Co., Ltd. All rights reserved.
*/
module huawei-ietf-system-deviations-NE8000M8M14 {
  namespace "urn:huawei:yang:huawei-ietf-system-deviations-NE8000M8M14";
  prefix sys-devs-NE8000M8M14;

  import ietf-system {
    prefix sys;
  }
  import ietf-inet-types {
    prefix inet;
  }

  organization
    "Huawei Technologies Co., Ltd.";
  contact
    "Huawei Industrial Base
     Bantian, Longgang
     Shenzhen 518129
     People's Republic of China
     Website: http://www.huawei.com
     Email: support@huawei.com";
  description
    "This module defines deviation statements for ietf-system module.";

  revision 2021-05-07 {
    description
      "Initial revision.";
    reference "Huawei private.";
  }

  deviation "/sys:system/sys:contact" {
    deviate not-supported;
  }
  deviation "/sys:system/sys:location" {
    deviate not-supported;
  }
  deviation "/sys:system/sys:clock/sys:timezone/sys:timezone-name" {
    deviate not-supported;
  }
  deviation "/sys:system/sys:dns-resolver" {
    deviate not-supported;
  }
  deviation "/sys:system/sys:radius" {
    deviate not-supported;
  }
  deviation "/sys:system/sys:authentication" {
    deviate not-supported;
  }
  deviation "/sys:system-state/sys:platform" {
    deviate not-supported;
  }
  deviation "/sys:system-restart" {
    deviate not-supported;
  }
  deviation "/sys:system-shutdown" {
    deviate not-supported;
  }
  deviation "/sys:system/sys:hostname" {
    deviate replace {
      type string {
        length "1..246";
      }
    }
    deviate add {
      default "HUAWEI";
    }
  }
  deviation "/sys:system/sys:clock/sys:timezone/sys:timezone-utc-offset/sys:timezone-utc-offset" {
    deviate replace {
      type int16 {
        range "-1080..1080";
      }
    }
    deviate add {
      default "0";
    }
  }
  deviation "/sys:system/sys:ntp/sys:server/sys:name" {
    deviate replace {
      type string {
        length "1..63";
      }
    }
  }
  deviation "/sys:system/sys:ntp/sys:server/sys:transport/sys:udp/sys:udp/sys:port" {
    deviate replace {
      type inet:port-number {
        range "123|1025..65535";
      }
    }
  }
  deviation "/sys:system/sys:ntp/sys:server/sys:association-type" {
    deviate replace {
      type enumeration {
        enum server {
          value 0;
          description
            "Use client association mode. This device
             will not provide synchronization to the
             configured NTP server.";
        }
        enum peer {
          value 1;
          description
            "Use symmetric active association mode.
             This device may provide synchronization
             to the configured NTP server.";
        }
      }
    }
  }
}
