/*
Copyright (C) 2021 Huawei Technologies Co., Ltd. All rights reserved.
*/
module huawei-ifm-atm-deviations-NE8000M8M14 {
  namespace "urn:huawei:yang:huawei-ifm-atm-deviations-NE8000M8M14";
  prefix ifm-atm-devs-NE8000M8M14;

  import huawei-ifm-atm {
    prefix ifm-atm;
  }
  import huawei-ifm {
    prefix ifm;
  }

  organization
    "Huawei Technologies Co., Ltd.";
  contact
    "Huawei Industrial Base
     Bantian, Longgang
     Shenzhen 518129
     People's Republic of China
     Website: http://www.huawei.com
     Email: support@huawei.com";
  description
    "This module defines deviation statements for huawei-ifm-atm module.";

  revision 2021-05-07 {
    description
      "Initial revision.";
    reference "Huawei private.";
  }

  deviation "/ifm:ifm/ifm:interfaces/ifm:interface/ifm-atm:atm" {
    deviate not-supported;
  }
}
